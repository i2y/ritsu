# 支払日, 支払の方針

# Specification: 支払日
- yuen.file: 支払.req
- yuen.version: 1
- yuen.description: テストの材料。版が二つある要件、置き換え、別のファイルの要件を元にした要件を書いたもの。例として決めた決まりで、実際の支払条件ではない

## month_end_close v1: 月末締め (yuen requirement)
請求書は月末で締める
- yuen.inForce: 2026-01-01..2027-03-31
- yuen.owner: 経理
- yuen.decided: decided 2025-12-01 by 経理 "締めを月末にそろえる。この材料のために決めたもの"
- yuen.waived: not verified "締め日は、月末の日付を返すだけなので、確かめる主張を置かない"
  approved 2026-10-03 by 経理 sha256:f96940c54fbf4ebe
- yuen.sha256: f96940c54fbf4ebe
- yuen.status: ok
- yuen satisfied by -> file "src/close.py"

## payment_day v1: 支払日 v1 (yuen requirement)
月末締め翌月末払い
- yuen.inForce: 2026-01-01..2027-03-31
- yuen.owner: 経理
- yuen.sha256: 48e56488e5f09eed
- yuen.status: ok
- yuen from -> payment_policy v1
- yuen satisfied by -> file "src/pay.py"
- yuen verified by -> file "tests/test_pay.py"

## payment_day v2: 支払日 v2 (yuen requirement)
20 日締め翌月 10 日払い
- yuen.inForce: 2027-04-01..
- yuen.owner: 経理
- yuen.decided: decided 2026-10-03 by 経理 "2027 年 4 月から、締めを 20 日に変える。この材料のために決めたもの"
- yuen.sha256: dfb59e69c88ea653
- yuen.status: ok
- yuen from -> payment_policy v1
- yuen satisfied by -> file "src/pay.py"
- yuen verified by -> file "tests/test_pay.py"
- yuen replaces -> month_end_close v1

# Specification: 支払の方針
- yuen.file: 方針.req
- yuen.version: 1
- yuen.description: テストの材料。支払日の要件の元になる方針を、例の約款から読んで決めたもの。例として書いたもので、実際の支払条件ではない

## payment_policy v1: 支払の方針 (yuen requirement)
受け取った請求書の代金は、締め日から 60 日以内に支払う
- yuen.owner: 経理
- yuen.decided: decided 2026-09-01 by 経理 "約款の第 4 条の「締め日から」を、締め日の翌日から数えると読む。この材料のために決めたもの"
- yuen.sha256: 2ad565ae8b811d54
- yuen.status: ok
- yuen from -> 約款
- yuen satisfied by -> file "src/pay.py"
- yuen verified by -> file "tests/test_pay.py"

# Specification: sources

## 約款 (yuen source)
- yuen.file: docs/約款.md
- yuen.url: https://example.org/terms.md
- yuen.sha256: 57a614edc586dc22

# Specification: artifacts

## file "src/close.py" (yuen artifact)
- yuen.sha256: 9bb0abb20fa56cb7
- yuen.end: file

## file "src/pay.py" (yuen artifact)
- yuen.sha256: 93e39b25842afd07
- yuen.end: file

## file "tests/test_pay.py" (yuen artifact)
- yuen.sha256: df4a7416b584ec48
- yuen.end: file
