# period_of_months

# Specification: period_of_months
- yuen.file: period_of_months.req
- yuen.version: 1
- yuen.description: Where the dates of koyomi's example period_of_months.cal could come from, if it followed the time rules of the USPTO's regulations in 37 CFR part 1. The sources are copied and pinned here, and what meets a requirement is read as a file. Written for this test material; it does not say how any rule is read

## date_of_receipt v1: date_of_receipt (yuen requirement)
Correspondence received in the Patent and Trademark Office is stamped with the date of receipt
- yuen.inForce: 2026-10-01..
- yuen.owner: legal
- yuen.waived: not verified "That the day of receipt is not counted is checked on koyomi doc's page, by reading the rule and its restatement side by side. This material has no claim that checks it"
  approved 2026-10-03 by legal sha256:c6a57f069e4638f2
- yuen.sha256: c6a57f069e4638f2
- yuen.status: ok
- yuen from -> cfr §1.6
- yuen satisfied by -> file "period_of_months.cal"

## timely_filing v1: timely_filing (yuen requirement)
Correspondence required to be filed within a set period of time is considered timely filed if it is mailed or transmitted before the period ends, with a certificate of the date of deposit or transmission
- yuen.inForce: 2026-10-01..
- yuen.owner: legal
- yuen.waived: not verified "A function that writes the rule's cases as they are, held against every origin of 2000 to 2027 and every month count of 1 to 12, was checked in koyomi's design stage. This material has no claim that checks it"
  approved 2026-10-03 by legal sha256:8d02c6a1f0ad3364
- yuen.sha256: 8d02c6a1f0ad3364
- yuen.status: ok
- yuen from -> cfr §1.8
- yuen from -> cfr §1.10
- yuen satisfied by -> file "period_of_months.cal"

## next_business_day v1: next_business_day (yuen requirement)
When the last day fixed for taking an action falls on a Saturday, Sunday or Federal holiday, the action may be taken on the next succeeding business day which is not one
- yuen.inForce: 2026-10-01..
- yuen.owner: legal
- yuen.decided: decided 2026-10-03 by legal "The next succeeding business day is read as the day after the closed day, and not moved further if that day is closed too. Decided for this material; it does not say how any rule is read"
- yuen.waived: not verified "koyomi's claim moved_on_or_after_last_day checks it, but this material reads the .cal as a file, so it does not name the claim"
  approved 2026-10-03 by legal sha256:8d9c6066ea40430f
- yuen.sha256: 8d9c6066ea40430f
- yuen.status: ok
- yuen from -> cfr §1.7
- yuen satisfied by -> file "period_of_months.cal"

# Specification: sources

## cfr §1.6 (yuen source)
§ 1.6 Receipt of correspondence.
(a) Date of receipt and Priority Mail Express® date of deposit. Correspondence received in the Patent and Trademark Office is stamped with the date of receipt except as follows:
(1) The Patent and Trademark Office is not open for the filing of correspondence on any day that is a Saturday, Sunday, or Federal holiday within the District of Columbia. Except for correspondence transmitted by facsimile under paragraph (a)(3) of this section, or filed electronically under paragraph (a)(4) of this section, no correspondence is received in the Office on Saturdays, Sundays, or Federal holidays within the District of Columbia.
(2) Correspondence filed in accordance with § 1.10 will be stamped with the date of deposit as Priority Mail Express® with the United States Postal Service.
(3) Correspondence transmitted by facsimile to the Patent and Trademark Office will be stamped with the date on which the complete transmission is received in the Patent and Trademark Office unless that date is a Saturday, Sunday, or Federal holiday within the District of Columbia, in which case the date stamped will be the next succeeding day which is not a Saturday, Sunday, or Federal holiday within the District of Columbia.
(4) Correspondence may be submitted using the USPTO patent electronic filing system only in accordance with the USPTO patent electronic filing system requirements. Correspondence officially submitted to the Office by way of the USPTO patent electronic filing system will be accorded a receipt date, which is the date in Eastern Time when the correspondence is received in the Office, regardless of whether that date is a Saturday, Sunday, or Federal holiday within the District of Columbia.
(b) [Reserved]
(c) Correspondence delivered by hand. In addition to being mailed, correspondence may be delivered by hand during hours the Office is open to receive correspondence.
(d) Facsimile transmission. Except in the cases enumerated below, correspondence, including authorizations to charge a deposit account, may be transmitted by facsimile. The receipt date accorded to the correspondence will be the date on which the complete transmission is received in the United States Patent and Trademark Office, unless that date is a Saturday, Sunday, or Federal holiday within the District of Columbia. See paragraph (a)(3) of this section. To facilitate proper processing, each transmission session should be limited to correspondence to be filed in a single application or other proceeding before the United States Patent and Trademark Office. The application number of a patent application, the control number of a reexamination or supplemental examination proceeding, the interference number of an interference proceeding, the trial number of a trial proceeding before the Board, or the patent number of a patent should be entered as a part of the sender's identification on a facsimile cover sheet. Facsimile transmissions are not permitted and, if submitted, will not be accorded a date of receipt in the following situations:
(1) [Reserved]
(2) Certified documents as specified in § 1.4(f);
(3) Correspondence that cannot receive the benefit of the certificate of mailing or transmission as specified in § 1.8(a)(2)(i)(A) through (D), (F), (I), and (K) and § 1.8(a)(2)(iii)(A), except that a continued prosecution application under § 1.53(d) may be transmitted to the Office by facsimile;
(4) Color drawings submitted under §§ 1.81, 1.83 through 1.85, 1.152, 1.165, 1.173, 1.437, or 1.1026;
(5) A request for reexamination under § 1.510 or § 1.913, or a request for supplemental examination under § 1.610;
(6) Correspondence to be filed in an application subject to a secrecy order under §§ 5.1 through 5.5 of this chapter and directly related to the secrecy order content of the application;
(7) In contested cases and trials before the Patent Trial and Appeal Board, except as the Board may expressly authorize.
(e) [Reserved]
(f) Facsimile transmission of a patent application under § 1.53(d). In the event that the Office has no evidence of receipt of an application under § 1.53(d) (a continued prosecution application) transmitted to the Office by facsimile transmission, the party who transmitted the application under § 1.53(d) may petition the Director to accord the application under § 1.53(d) a filing date as of the date the application under § 1.53(d) is shown to have been transmitted to and received in the Office,
(1) Provided that the party who transmitted such application under § 1.53(d):
(i) Informs the Office of the previous transmission of the application under § 1.53(d) promptly after becoming aware that the Office has no evidence of receipt of the application under § 1.53(d);
(ii) Supplies an additional copy of the previously transmitted application under § 1.53(d); and
(iii) Includes a statement which attests on a personal knowledge basis or to the satisfaction of the Director to the previous transmission of the application under § 1.53(d) and is accompanied by a copy of the sending unit's report confirming transmission of the application under § 1.53(d) or evidence that came into being after the complete transmission and within one business day of the complete transmission of the application under § 1.53(d).
(2) The Office may require additional evidence to determine if the application under § 1.53(d) was transmitted to and received in the Office on the date in question.
(g) Submission of the national stage correspondence required by § 1.495 via the USPTO patent electronic filing system . In the event that the Office has no evidence of receipt of the national stage correspondence required by § 1.495, which was submitted to the Office by the USPTO patent electronic filing system, the party who submitted the correspondence may petition the Director to accord the national stage correspondence a receipt date as of the date the correspondence is shown to have been officially submitted to the Office.
(1) The petition of this paragraph (g) requires that the party who submitted such national stage correspondence:
(i) Informs the Office of the previous submission of the correspondence promptly after becoming aware that the Office has no evidence of receipt of the correspondence under § 1.495;
(ii) Supplies an additional copy of the previously submitted correspondence;
(iii) Includes a statement that attests on a personal knowledge basis, or to the satisfaction of the Director, that the correspondence was previously officially submitted; and
(iv) Supplies a copy of an acknowledgment receipt generated by the USPTO patent electronic filing system, or equivalent evidence, confirming the submission to support the statement of paragraph (g)(1)(iii) of this section.
(2) The Office may require additional evidence to determine if the national stage correspondence was submitted to the Office on the date in question.
[58 FR 54501, Oct. 22, 1993; 58 FR 64154, Dec. 6, 1993; 61 FR 56447, Nov. 1, 1996; 62 FR 53180, Oct. 10, 1997; 64 FR 48917, Sept. 8, 1999; 65 FR 54657, Sept. 8, 2000; 65 FR 76772, Dec. 7, 2000; 68 FR 14336, Mar. 25, 2003; 68 FR 48288, Aug. 13, 2003; 69 FR 49997, Aug. 12, 2004; 69 FR 56536, Sept. 21, 2004; 72 FR 2775, Jan. 23, 2007; 77 FR 42173, July 17, 2012; 77 FR 46624, Aug. 6, 2012; 78 FR 62394, Oct. 21, 2013; 79 FR 63039, Oct. 22, 2014; 80 FR 17952, Apr. 2, 2015; 86 FR 35229, July 2, 2021; 87 FR 68904, Nov. 17, 2022]
- yuen.law: ecfr 37 CFR 1
- yuen.asof: 2026-01-01
- yuen.sha256: 6bcdc27c3428886c

## cfr §1.7 (yuen source)
§ 1.7 Times for taking action; Expiration on Saturday, Sunday or Federal holiday.
(a) Whenever periods of time are specified in this part in days, calendar days are intended. When the day, or the last day fixed by statute or by or under this part for taking any action or paying any fee in the United States Patent and Trademark Office falls on Saturday, Sunday, or on a Federal holiday within the District of Columbia, the action may be taken, or the fee paid, on the next succeeding business day which is not a Saturday, Sunday, or a Federal holiday. See § 90.3 of this chapter for time for appeal or for commencing civil action.
(b) If the day that is twelve months after the filing date of a provisional application under 35 U.S.C. 111(b) and § 1.53(c) falls on Saturday, Sunday, or on a Federal holiday within the District of Columbia, the period of pendency shall be extended to the next succeeding secular or business day which is not a Saturday, Sunday, or a Federal holiday.
[65 FR 14871, Mar. 20, 2000, as amended at 78 FR 62395, Oct. 21, 2013]
- yuen.law: ecfr 37 CFR 1
- yuen.asof: 2026-01-01
- yuen.sha256: 01de176ebe4740d7

## cfr §1.8 (yuen source)
§ 1.8 Certificate of mailing or transmission.
(a) Except in the situations enumerated in paragraph (a)(2) of this section or as otherwise expressly excluded in this chapter, correspondence required to be filed in the U.S. Patent and Trademark Office within a set period of time will be considered as being timely filed if the procedure described in this section is followed. The actual date of receipt will be used for all other purposes.
(1) Correspondence will be considered as being timely filed if:
(i) The correspondence is mailed or transmitted prior to expiration of the set period of time by being:
(A) Addressed as set out in § 1.1(a) and deposited with the U.S. Postal Service with sufficient postage as first class mail;
(B) Transmitted by facsimile to the Patent and Trademark Office in accordance with § 1.6(d); or
(C) Transmitted via the USPTO patent electronic filing system in accordance with § 1.6(a)(4); and
(ii) The correspondence includes a certificate for each piece of correspondence stating the date of deposit or transmission. The person signing the certificate should have reasonable basis to expect that the correspondence would be mailed or transmitted on or before the date indicated.
(2) The procedure described in paragraph (a)(1) of this section does not apply to, and no benefit will be given to a Certificate of Mailing or Transmission on the following:
(i) Relative to Patents and Patent Applications—
(A) The filing of a national patent application specification and drawing or other correspondence for the purpose of obtaining an application filing date, including a request for a continued prosecution application under § 1.53(d);
(B) Papers filed in trials before the Patent Trial and Appeal Board, which are governed by § 42.6(b) of this title;
(C) Papers filed in contested cases before the Patent Trial and Appeal Board, which are governed by § 41.106 (f) of this title;
(D) The filing of an international application for patent;
(E) The filing of correspondence in an international application before the U.S. Receiving Office, the U.S. International Searching Authority, or the U.S. International Preliminary Examining Authority;
(F) The filing of a copy of the international application and the basic national fee necessary to enter the national stage, as specified in § 1.495(b).
(G) The filing of a written declaration of abandonment under § 1.138;
(H) The filing of a submission under § 1.217 for publication of a redacted copy of an application;
(I) The filing of a third-party submission under § 1.290;
(J) The calculation of any period of adjustment, as specified in § 1.703(f); and
(K) The filing of an international design application.
(ii) [Reserved]
(iii) Relative to Disciplinary Proceedings—
(A) Correspondence filed in connection with a disciplinary proceeding under part 11 of this chapter.
(B) [Reserved]
(b) In the event that correspondence is considered timely filed by being mailed or transmitted in accordance with paragraph (a) of this section, but not received in the U.S. Patent and Trademark Office after a reasonable amount of time has elapsed from the time of mailing or transmitting of the correspondence, or after the application is held to be abandoned, or after the proceeding is dismissed or decided with prejudice, or the prosecution of a reexamination proceeding is terminated pursuant to § 1.550(d) or § 1.957(b) or limited pursuant to § 1.957(c), or a requester paper is refused consideration pursuant to § 1.957(a), the correspondence will be considered timely if the party who forwarded such correspondence:
(1) Informs the Office of the previous mailing or transmission of the correspondence promptly after becoming aware that the Office has no evidence of receipt of the correspondence;
(2) Supplies an additional copy of the previously mailed or transmitted correspondence and certificate; and
(3) Includes a statement that attests on a personal knowledge basis or to the satisfaction of the Director to the previous timely mailing, transmission or submission. If the correspondence was sent by facsimile transmission, a copy of the sending unit's report confirming transmission may be used to support this statement. If the correspondence was transmitted via the USPTO patent electronic filing system , a copy of an acknowledgment receipt generated by the USPTO patent electronic filing system confirming submission may be used to support this statement.
(c) The Office may require additional evidence to determine if the correspondence was timely filed.
[58 FR 54502, Oct. 22, 1993; 58 FR 64154, Dec. 6, 1993, as amended at 61 FR 56447, Nov. 1, 1996; 62 FR 53181, Oct. 10, 1997; 67 FR 523, Jan. 4, 2002; 68 FR 48288, Aug. 13, 2003; 69 FR 49997, Aug. 12, 2004; 69 FR 56536, Sept. 21, 2004; 72 FR 2775, Jan. 23, 2007; 72 FR 18904, Apr. 16, 2007; 73 FR 47684, Aug. 14, 2008; 77 FR 42173, July 17, 2012; 80 FR 17953, Apr. 2, 2015]
- yuen.law: ecfr 37 CFR 1
- yuen.asof: 2026-01-01
- yuen.sha256: fa698e3ea7cb1e49

## cfr §1.10 (yuen source)
§ 1.10 Filing of correspondence by Priority Mail Express®.
(a)(1) Any correspondence received by the U.S. Patent and Trademark Office (USPTO) that was delivered by the Priority Mail Express® Post Office to Addressee service of the United States Postal Service (USPS) will be considered filed with the USPTO on the date of deposit with the USPS.
(2) The date of deposit with USPS is shown by the “date accepted” on the Priority Mail Express® label or other official USPS notation. If the USPS deposit date cannot be determined, the correspondence will be accorded the USPTO receipt date as the filing date. See § 1.6(a).
(b) Correspondence should be deposited directly with an employee of the USPS to ensure that the person depositing the correspondence receives a legible copy of the Priority Mail Express® mailing label with the “date accepted” clearly marked. Persons dealing indirectly with the employees of the USPS (such as by deposit in a Priority Mail Express® drop box) do so at the risk of not receiving a copy of the Priority Mail Express® mailing label with the desired “date accepted” clearly marked. The paper(s) or fee(s) that constitute the correspondence should also include the Priority Mail Express® mailing label number thereon. See paragraphs (c), (d) and (e) of this section.
(c) Any person filing correspondence under this section that was received by the Office and delivered by the Priority Mail Express® Post Office to Addressee service of the USPS, who can show that there is a discrepancy between the filing date accorded by the Office to the correspondence and the date of deposit as shown by the “date accepted” on the Priority Mail Express® mailing label or other official USPS notation, may petition the Director to accord the correspondence a filing date as of the “date accepted” on the Priority Mail Express® mailing label or other official USPS notation, provided that:
(1) The petition is filed promptly after the person becomes aware that the Office has accorded, or will accord, a filing date other than the USPS deposit date;
(2) The number of the Priority Mail Express® mailing label was placed on the paper(s) or fee(s) that constitute the correspondence prior to the original mailing by Priority Mail Express®; and
(3) The petition includes a true copy of the Priority Mail Express® mailing label showing the “date accepted,” and of any other official notation by the USPS relied upon to show the date of deposit.
(d) Any person filing correspondence under this section that was received by the Office and delivered by the Priority Mail Express® Post Office to Addressee service of the USPS, who can show that the “date accepted” on the Priority Mail Express® mailing label or other official notation entered by the USPS was incorrectly entered or omitted by the USPS, may petition the Director to accord the correspondence a filing date as of the date the correspondence is shown to have been deposited with the USPS, provided that:
(1) The petition is filed promptly after the person becomes aware that the Office has accorded, or will accord, a filing date based upon an incorrect entry by the USPS;
(2) The number of the Priority Mail Express® mailing label was placed on the paper(s) or fee(s) that constitute the correspondence prior to the original mailing by Priority Mail Express®; and
(3) The petition includes a showing which establishes, to the satisfaction of the Director, that the requested filing date was the date the correspondence was deposited in the Priority Mail Express® Post Office to Addressee service prior to the last scheduled pickup for that day. Any showing pursuant to this paragraph must be corroborated by evidence from the USPS or that came into being after deposit and within one business day of the deposit of the correspondence in the Priority Mail Express® Post Office to Addressee service of the USPS.
(e) Any person mailing correspondence addressed as set out in § 1.1(a) to the Office with sufficient postage utilizing the Priority Mail Express® Post Office to Addressee service of the USPS but not received by the Office, may petition the Director to consider such correspondence filed in the Office on the USPS deposit date, provided that:
(1) The petition is filed promptly after the person becomes aware that the Office has no evidence of receipt of the correspondence;
(2) The number of the Priority Mail Express® mailing label was placed on the paper(s) or fee(s) that constitute the correspondence prior to the original mailing by Priority Mail Express®;
(3) The petition includes a copy of the originally deposited paper(s) or fee(s) that constitute the correspondence showing the number of the Priority Mail Express® mailing label thereon, a copy of any returned postcard receipt, a copy of the Priority Mail Express® mailing label showing the “date accepted,” a copy of any other official notation by the USPS relied upon to show the date of deposit, and, if the requested filing date is a date other than the “date accepted” on the Priority Mail Express® mailing label or other official notation entered by the USPS, a showing pursuant to paragraph (d)(3) of this section that the requested filing date was the date the correspondence was deposited in the Priority Mail Express® Post Office to Addressee service prior to the last scheduled pickup for that day; and
(4) The petition includes a statement which establishes, to the satisfaction of the Director, the original deposit of the correspondence and that the copies of the correspondence, the copy of the Priority Mail Express® mailing label, the copy of any returned postcard receipt, and any official notation entered by the USPS are true copies of the originally mailed correspondence, original Priority Mail Express® mailing label, returned postcard receipt, and official notation entered by the USPS.
(f) The Office may require additional evidence to determine if the correspondence was deposited as Priority Mail Express® with the USPS on the date in question.
(g) Any person who mails correspondence addressed as set out in § 1.1(a) to the Office with sufficient postage utilizing the Priority Mail Express® Post Office to Addressee service of the USPS, but has the correspondence returned by the USPS due to an interruption or emergency in Priority Mail Express® service, may petition the Director to consider such correspondence as filed on a particular date in the Office, provided that:
(1) The petition is filed promptly after the person becomes aware of the return of the correspondence;
(2) The number of the Priority Mail Express® mailing label was placed on the paper(s) or fee(s) that constitute the correspondence prior to the original mailing by Priority Mail Express®;
(3) The petition includes the original correspondence or a copy of the original correspondence showing the number of the Priority Mail Express® mailing label thereon and a copy of the Priority Mail Express® mailing label showing the “date accepted”; and
(4) The petition includes a statement which establishes, to the satisfaction of the Director, the original deposit of the correspondence and that the correspondence or copy of the correspondence is the original correspondence or a true copy of the correspondence originally deposited with the USPS on the requested filing date. The Office may require additional evidence to determine if the correspondence was returned by the USPS due to an interruption or emergency in Priority Mail Express® service.
(h) Any person who attempts to mail correspondence addressed as set out in § 1.1(a) to the Office with sufficient postage utilizing the Priority Mail Express® Post Office to Addressee service of the USPS, but has the correspondence refused by an employee of the USPS due to an interruption or emergency in Priority Mail Express® service, may petition the Director to consider such correspondence as filed on a particular date in the Office, provided that:
(1) The petition is filed promptly after the person becomes aware of the refusal of the correspondence;
(2) The number of the Priority Mail Express® mailing label was placed on the paper(s) or fee(s) that constitute the correspondence prior to the attempted mailing by Priority Mail Express®;
(3) The petition includes the original correspondence or a copy of the original correspondence showing the number of the Priority Mail Express® mailing label thereon; and
(4) The petition includes a statement by the person who originally attempted to deposit the correspondence with the USPS which establishes, to the satisfaction of the Director, the original attempt to deposit the correspondence and that the correspondence or copy of the correspondence is the original correspondence or a true copy of the correspondence originally attempted to be deposited with the USPS on the requested filing date. The Office may require additional evidence to determine if the correspondence was refused by an employee of the USPS due to an interruption or emergency in Priority Mail Express® service.
(i) Any person attempting to file correspondence under this section that was unable to be deposited with the USPS due to an interruption or emergency in Priority Mail Express® service which has been so designated by the Director, may petition the Director to consider such correspondence as filed on a particular date in the Office, provided that:
(1) The petition is filed in a manner designated by the Director promptly after the person becomes aware of the designated interruption or emergency in Priority Mail Express® service;
(2) The petition includes the original correspondence or a copy of the original correspondence; and
(3) The petition includes a statement which establishes, to the satisfaction of the Director, that the correspondence would have been deposited with the USPS but for the designated interruption or emergency in Priority Mail Express® service, and that the correspondence or copy of the correspondence is the original correspondence or a true copy of the correspondence originally attempted to be deposited with the USPS on the requested filing date.
[79 FR 63039, Oct. 22, 2014]
- yuen.law: ecfr 37 CFR 1
- yuen.asof: 2026-01-01
- yuen.sha256: 5adcbc193371fd26

# Specification: artifacts

## file "period_of_months.cal" (yuen artifact)
- yuen.sha256: 0f1a06d9b71a39f6
- yuen.end: file
