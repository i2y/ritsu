# delivery

# Specification: delivery
- yuen.file: delivery.req
- yuen.version: 1
- yuen.description: A test material: the tasks and records of dandori's example arrange_delivery.flow, named by where in the delivery procedure they come from

## next_day v1: next_day (yuen requirement)
A next-day parcel is booked with a carrier. When no van is free, it says so and stops
- yuen.owner: logistics
- yuen.waived: not verified "This material has no claim that runs the workflow"
  approved 2026-10-04 by logistics sha256:854ea074c3b4093e
- yuen.sha256: 854ea074c3b4093e
- yuen.status: ok
- yuen from -> procedure
- yuen satisfied by -> dandori "arrange_delivery.flow" task book_next_day

## regular v1: regular (yuen requirement)
A standard parcel is booked with the post
- yuen.owner: logistics
- yuen.waived: not verified "This material has no claim that runs the workflow"
  approved 2026-10-04 by logistics sha256:2d8beaedbaa117d5
- yuen.sha256: 2d8beaedbaa117d5
- yuen.status: ok
- yuen from -> procedure
- yuen satisfied by -> dandori "arrange_delivery.flow" task book_standard

## tracking_number v1: tracking_number (yuen requirement)
Either way, a tracking number is returned
- yuen.owner: logistics
- yuen.waived: not verified "This material has no claim that runs the workflow"
  approved 2026-10-04 by logistics sha256:42d300c1d0357478
- yuen.sha256: 42d300c1d0357478
- yuen.status: ok
- yuen from -> procedure
- yuen satisfied by -> dandori "arrange_delivery.flow" record Booking field tracking_number
- yuen satisfied by -> dandori "arrange_delivery.flow" output tracking_number

# Specification: sources

## procedure (yuen source)
- yuen.file: delivery_procedure.md
- yuen.sha256: 9a98840e2a559185

# Specification: artifacts

## dandori "arrange_delivery.flow" task book_next_day (yuen artifact)
- yuen.sha256: 06fdb81a96fb18d4
- yuen.end: item

## dandori "arrange_delivery.flow" task book_standard (yuen artifact)
- yuen.sha256: 9275484a06b3b217
- yuen.end: item

## dandori "arrange_delivery.flow" record Booking field tracking_number (yuen artifact)
- yuen.sha256: a65b57058f985f17
- yuen.end: item

## dandori "arrange_delivery.flow" output tracking_number (yuen artifact)
- yuen.sha256: a65b57058f985f17
- yuen.end: item
