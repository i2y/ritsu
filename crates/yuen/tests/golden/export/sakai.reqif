# 受注の用語

# Specification: 受注の用語
- yuen.file: 受注の用語.req
- yuen.version: 1
- yuen.description: sakai の例のコンテキスト「受注.ctx」の語が、用語集のどこから来たかを書いたテストの材料

## order v1: 注文 (yuen requirement)
注文は、客が確定させた購入の申し込みで、取り消されても消えない
- yuen.owner: 受注
- yuen.waived: not verified "この材料は、語の使われ方を確かめる主張を持たない"
  approved 2026-10-04 by 受注 sha256:1f47e05b6d46c563
- yuen.sha256: 1f47e05b6d46c563
- yuen.status: ok
- yuen from -> 用語集
- yuen satisfied by -> sakai "contexts/受注.ctx" term 注文

## cancel v1: キャンセル (yuen requirement)
キャンセルは、出荷の前に、客の申し出で注文を取り消すこと
- yuen.owner: 受注
- yuen.waived: not verified "この材料は、語の使われ方を確かめる主張を持たない"
  approved 2026-10-04 by 受注 sha256:a622512a90fba0e5
- yuen.sha256: a622512a90fba0e5
- yuen.status: ok
- yuen from -> 用語集
- yuen satisfied by -> sakai "contexts/受注.ctx" term キャンセル

# Specification: sources

## 用語集 (yuen source)
- yuen.file: 用語集.md
- yuen.sha256: ada090e1ea2e7b68

# Specification: artifacts

## sakai "contexts/受注.ctx" term 注文 (yuen artifact)
- yuen.sha256: 1b2bb352a123c296
- yuen.end: item

## sakai "contexts/受注.ctx" term キャンセル (yuen artifact)
- yuen.sha256: dbfd211b7e4cef4b
- yuen.end: item
