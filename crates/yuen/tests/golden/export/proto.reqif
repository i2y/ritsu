# 在庫

# Specification: 在庫
- yuen.file: 在庫.req
- yuen.version: 1
- yuen.description: dandori の例 fulfillment の倉庫と出荷のサービスの約束を、.proto の要素を指して書いたテストの材料。出典は約束の文書を保存して固定する

## reserve v1: 在庫を押さえる (yuen requirement)
倉庫は、注文の一行ごとに在庫を押さえる。足りなければ、押さえずに足りないと答える
- yuen.owner: 倉庫
- yuen.waived: not verified "この材料は、サービスを走らせる主張を持たない"
  approved 2026-10-04 by 倉庫 sha256:e10350fc1754b540
- yuen.sha256: e10350fc1754b540
- yuen.status: ok
- yuen from -> 約束
- yuen satisfied by -> proto "warehouse.proto" service StockService method Reserve
- yuen satisfied by -> proto "warehouse.proto" enum Stock

## release v1: 押さえを放す (yuen requirement)
押さえた在庫は、押さえたときの番号で放せる
- yuen.owner: 倉庫
- yuen.waived: not verified "この材料は、サービスを走らせる主張を持たない"
  approved 2026-10-04 by 倉庫 sha256:e4cf3d1ba8da98bf
- yuen.sha256: e4cf3d1ba8da98bf
- yuen.status: ok
- yuen from -> 約束
- yuen satisfied by -> proto "warehouse.proto" service StockService method Release

## fulfill v1: 出荷 (yuen requirement)
出荷は、注文を受けて始まり、押さえた在庫と追跡番号を答える
- yuen.owner: 倉庫
- yuen.waived: not verified "この材料は、サービスを走らせる主張を持たない"
  approved 2026-10-04 by 倉庫 sha256:a56299dbcadd3c9f
- yuen.sha256: a56299dbcadd3c9f
- yuen.status: ok
- yuen from -> 約束
- yuen satisfied by -> proto "fulfillment.proto" service FulfillmentService method Fulfill
- yuen satisfied by -> proto "fulfillment.proto" message FulfillResponse field tracking_number

# Specification: sources

## 約束 (yuen source)
- yuen.file: 約束.md
- yuen.sha256: 6876e197cbb677f0

# Specification: artifacts

## proto "warehouse.proto" service StockService method Reserve (yuen artifact)
- yuen.sha256: cadb2fc727e9af81
- yuen.end: item

## proto "warehouse.proto" enum Stock (yuen artifact)
- yuen.sha256: d7450e7503c905f7
- yuen.end: item

## proto "warehouse.proto" service StockService method Release (yuen artifact)
- yuen.sha256: 2a0912a66889e515
- yuen.end: item

## proto "fulfillment.proto" service FulfillmentService method Fulfill (yuen artifact)
- yuen.sha256: 6c73e17bf5bedba7
- yuen.end: item

## proto "fulfillment.proto" message FulfillResponse field tracking_number (yuen artifact)
- yuen.sha256: fb7f7e2617539e54
- yuen.end: item
