# fire_extinguishers, 印紙税

# Specification: fire_extinguishers
- yuen.file: fire_extinguishers.req
- yuen.version: 1
- yuen.description: Where the distances of the rulec corpus rule osha_extinguisher.rule come from: 29 CFR 1910.157(d), borrowed from the copy the rule pins. A test fixture; it does not say how the regulation is to be read

## travel_distance v1: travel_distance (yuen requirement)
Portable fire extinguishers for Class A hazards are placed so that the travel distance to any extinguisher is 75 feet or less, and for Class B hazards 50 feet or less
- yuen.inForce: 2026-01-01..
- yuen.owner: safety
- yuen.waived: not verified "rulec checks that the table covers every hazard; this fixture names no claim"
  approved 2026-10-04 by safety sha256:849dc53f1d112c23
- yuen.sha256: 849dc53f1d112c23
- yuen.status: ok
- yuen from -> osha §1910.157
- yuen satisfied by -> rulec "rules/osha_extinguisher.rule" table distance

# Specification: 印紙税
- yuen.file: 印紙税.req
- yuen.version: 1
- yuen.description: rulec のコーパスの規則「印紙税の本則と軽減.rule」の表が、印紙税法と租税特別措置法のどこから来たかを書いたテストの材料。出典は自分で保存して固定し（コピーは規則のコピーと同じバイト列）、成果物は規則の表と節を一つずつ指す。例として書いたもので、法令の読み方を示すものではない

## base_tax v1: 本則の税額 (yuen requirement)
不動産の譲渡に関する契約書の印紙税額は、記載された契約金額に応じて、別表第一の第1号文書の欄の税率による。契約金額が1万円未満のものは課税しない
- yuen.inForce: 2026-04-01..
- yuen.owner: 税務
- yuen.waived: not verified "表が契約金額のすべてを覆い、行が重ならないことは rulec の検査が確かめる。この材料は、それを指す主張を持たない"
  approved 2026-10-04 by 税務 sha256:56d4ef0ae01ebb19
- yuen.sha256: 56d4ef0ae01ebb19
- yuen.status: ok
- yuen from -> 法 別表第一
- yuen satisfied by -> rulec "rules/印紙税の本則と軽減.rule" table 本則
- yuen satisfied by -> rulec "rules/印紙税の本則と軽減.rule" clause 非課税

## reduced_rate v1: 軽減税率 (yuen requirement)
令和9年3月31日までに作成される不動産の譲渡に関する契約書の印紙税額は、租税特別措置法第91条の軽減された税率による
- yuen.inForce: 2026-04-01..
- yuen.owner: 税務
- yuen.waived: not verified "軽減の表が本則の表より先に当たることは rulec の検査が確かめる。この材料は、それを指す主張を持たない"
  approved 2026-10-04 by 税務 sha256:c3fbde1529c44e2e
- yuen.sha256: c3fbde1529c44e2e
- yuen.status: ok
- yuen from -> 措置法 第91条
- yuen satisfied by -> rulec "rules/印紙税の本則と軽減.rule" table 軽減
- yuen satisfied by -> rulec "rules/印紙税の本則と軽減.rule" define 軽減期間

# Specification: sources

## osha §1910.157 (yuen source)
§ 1910.157 Portable fire extinguishers.
(a) Scope and application. The requirements of this section apply to the placement, use, maintenance, and testing of portable fire extinguishers provided for the use of employees. Paragraph (d) of this section does not apply to extinguishers provided for employee use on the outside of workplace buildings or structures. Where extinguishers are provided but are not intended for employee use and the employer has an emergency action plan and a fire prevention plan that meet the requirements of 29 CFR 1910.38 and 29 CFR 1910.39 respectively, then only the requirements of paragraphs (e) and (f) of this section apply.
(b) Exemptions. (1) Where the employer has established and implemented a written fire safety policy which requires the immediate and total evacuation of employees from the workplace upon the sounding of a fire alarm signal and which includes an emergency action plan and a fire prevention plan which meet the requirements of 29 CFR 1910.38 and 29 CFR 1910.39 respectively, and when extinguishers are not available in the workplace, the employer is exempt from all requirements of this section unless a specific standard in part 1910 requires that a portable fire extinguisher be provided.
(2) Where the employer has an emergency action plan meeting the requirements of § 1910.38 which designates certain employees to be the only employees authorized to use the available portable fire extinguishers, and which requires all other employees in the fire area to immediately evacuate the affected work area upon the sounding of the fire alarm, the employer is exempt from the distribution requirements in paragraph (d) of this section.
(c) General requirements. (1) The employer shall provide portable fire extinguishers and shall mount, locate and identify them so that they are readily accessible to employees without subjecting the employees to possible injury.
(2) Only approved portable fire extinguishers shall be used to meet the requirements of this section.
(3) The employer shall not provide or make available in the workplace portable fire extinguishers using carbon tetrachloride or chlorobromomethane extinguishing agents.
(4) The employer shall assure that portable fire extinguishers are maintained in a fully charged and operable condition and kept in their designated places at all times except during use.
(5) The employer shall remove from service all soldered or riveted shell self-generating soda acid or self-generating foam or gas cartridge water type portable fire extinguishers which are operated by inverting the extinguisher to rupture the cartridge or to initiate an uncontrollable pressure generating chemical reaction to expel the agent.
(d) Selection and distribution. (1) Portable fire extinguishers shall be provided for employee use and selected and distributed based on the classes of anticipated workplace fires and on the size and degree of hazard which would affect their use.
(2) The employer shall distribute portable fire extinguishers for use by employees on Class A fires so that the travel distance for employees to any extinguisher is 75 feet (22.9 m) or less.
(3) The employer may use uniformly spaced standpipe systems or hose stations connected to a sprinkler system installed for emergency use by employees instead of Class A portable fire extinguishers, provided that such systems meet the respective requirements of § 1910.158 or § 1910.159, that they provide total coverage of the area to be protected, and that employees are trained at least annually in their use.
(4) The employer shall distribute portable fire extinguishers for use by employees on Class B fires so that the travel distance from the Class B hazard area to any extinguisher is 50 feet (15.2 m) or less.
(5) The employer shall distribute portable fire extinguishers used for Class C hazards on the basis of the appropriate pattern for the existing Class A or Class B hazards.
(6) The employer shall distribute portable fire extinguishers or other containers of Class D extinguishing agent for use by employees so that the travel distance from the combustible metal working area to any extinguishing agent is 75 feet (22.9 m) or less. Portable fire extinguishers for Class D hazards are required in those combustible metal working areas where combustible metal powders, flakes, shavings, or similarly sized products are generated at least once every two weeks.
(e) Inspection, maintenance and testing. (1) The employer shall be responsible for the inspection, maintenance and testing of all portable fire extinguishers in the workplace.
(2) Portable extinguishers or hose used in lieu thereof under paragraph (d)(3) of this section shall be visually inspected monthly.
(3) The employer shall assure that portable fire extinguishers are subjected to an annual maintenance check. Stored pressure extinguishers do not require an internal examination. The employer shall record the annual maintenance date and retain this record for one year after the last entry or the life of the shell, whichever is less. The record shall be available to the Assistant Secretary upon request.
(4) The employer shall assure that stored pressure dry chemical extinguishers that require a 12-year hydrostatic test are emptied and subjected to applicable maintenance procedures every 6 years. Dry chemical extinguishers having non-refillable disposable containers are exempt from this requirement. When recharging or hydrostatic testing is performed, the 6-year requirement begins from that date.
(5) The employer shall assure that alternate equivalent protection is provided when portable fire extinguishers are removed from service for maintenance and recharging.
(f) Hydrostatic testing. (1) The employer shall assure that hydrostatic testing is performed by trained persons with suitable testing equipment and facilities.
(2) The employer shall assure that portable extinguishers are hydrostatically tested at the intervals listed in Table L-1 of this section, except under any of the following conditions:
(i) When the unit has been repaired by soldering, welding, brazing, or use of patching compounds;
(ii) When the cylinder or shell threads are damaged;
(iii) When there is corrosion that has caused pitting, including corrosion under removable name plate assemblies;
(iv) When the extinguisher has been burned in a fire; or
(v) When a calcium chloride extinguishing agent has been used in a stainless steel shell.
(3) In addition to an external visual examination, the employer shall assure that an internal examination of cylinders and shells to be tested is made prior to the hydrostatic tests.
Table L-1
Type of extinguishers
Test interval (years)
Soda acid (soldered brass shells) (until 1/1/82)
(1)
Soda acid (stainless steel shell)
5
Cartridge operated water and/or antifreeze
5
Stored pressure water and/or antifreeze
5
Wetting agent
5
Foam (soldered brass shells) (until 1/1/82)
(1)
Foam (stainless steel shell)
5
Aqueous Film Forming foam (AFFF)
5
Loaded stream
5
Dry chemical with stainless steel
5
Carbon dioxide
5
Dry chemical, stored pressure, with mild steel, brazed brass or aluminum shells
12
Dry chemical, cartridge or cylinder operated, with mild steel shells
12
Halon 1211
12
Halon 1301
12
Dry powder, cartridge or cylinder operated with mild steel shells
12
1 Extinguishers having shells constructed of copper or brass joined by soft solder or rivets shall not be hydrostatically tested and shall be removed from service by January 1, 1982. (Not permitted)
(4) The employer shall assure that portable fire extinguishers are hydrostatically tested whenever they show new evidence of corrosion or mechanical injury, except under the conditions listed in paragraphs (f)(2)(i)-(v) of this section.
(5) The employer shall assure that hydrostatic tests are performed on extinguisher hose assemblies which are equipped with a shut-off nozzle at the discharge end of the hose. The test interval shall be the same as specified for the extinguisher on which the hose is installed.
(6) The employer shall assure that carbon dioxide hose assemblies with a shut-off nozzle are hydrostatically tested at 1,250 psi (8,620 kPa).
(7) The employer shall assure that dry chemical and dry powder hose assemblies with a shut-off nozzle are hydrostatically tested at 300 psi (2,070 kPa).
(8) Hose assemblies passing a hydrostatic test do not require any type of recording or stamping.
(9) The employer shall assure that hose assemblies for carbon dioxide extinguishers that require a hydrostatic test are tested within a protective cage device.
(10) The employer shall assure that carbon dioxide extinguishers and nitrogen or carbon dioxide cylinders used with wheeled extinguishers are tested every 5 years at 5/3 of the service pressure as stamped into the cylinder. Nitrogen cylinders which comply with 49 CFR 173.34(e)(15) may be hydrostatically tested every 10 years.
(11) The employer shall assure that all stored pressure and Halon 1211 types of extinguishers are hydrostatically tested at the factory test pressure not to exceed two times the service pressure.
(12) The employer shall assure that acceptable self-generating type soda acid and foam extinguishers are tested at 350 psi (2,410 kPa).
(13) Air or gas pressure may not be used for hydrostatic testing.
(14) Extinguisher shells, cylinders, or cartridges which fail a hydrostatic pressure test, or which are not fit for testing shall be removed from service and from the workplace.
(15)(i) The equipment for testing compressed gas type cylinders shall be of the water jacket type. The equipment shall be provided with an expansion indicator which operates with an accuracy within one percent of the total expansion or .1cc (.1mL) of liquid.
(ii) The equipment for testing non-compressed gas type cylinders shall consist of the following:
(A) A hydrostatic test pump, hand or power operated, capable of producing not less than 150 percent of the test pressure, which shall include appropriate check valves and fittings;
(B) A flexible connection for attachment to fittings to test through the extinguisher nozzle, test bonnet, or hose outlet, as is applicable; and
(C) A protective cage or barrier for personal protection of the tester, designed to provide visual observation of the extinguisher under test.
(16) The employer shall maintain and provide upon request to the Assistant Secretary evidence that the required hydrostatic testing of fire extinguishers has been performed at the time intervals shown in Table L-1. Such evidence shall be in the form of a certification record which includes the date of the test, the signature of the person who performed the test and the serial number, or other identifier, of the fire extinguisher that was tested. Such records shall be kept until the extinguisher is hydrostatically retested at the time interval specified in Table L-1 or until the extinguisher is taken out of service, whichever comes first.
(g) Training and education. (1) Where the employer has provided portable fire extinguishers for employee use in the workplace, the employer shall also provide an educational program to familiarize employees with the general principles of fire extinguisher use and the hazards involved with incipient stage fire fighting.
(2) The employer shall provide the education required in paragraph (g)(1) of this section upon initial employment and at least annually thereafter.
(3) The employer shall provide employees who have been designated to use fire fighting equipment as part of an emergency action plan with training in the use of the appropriate equipment.
(4) The employer shall provide the training required in paragraph (g)(3) of this section upon initial assignment to the designated group of employees and at least annually thereafter.
[45 FR 60708, Sept. 12, 1980; 46 FR 24557, May 1, 1981, as amended at 51 FR 34560, Sept. 29, 1986; 61 FR 9239, Mar. 7, 1996; 67 FR 67964, Nov. 7, 2002]
- yuen.law: ecfr 29 CFR 1910
- yuen.asof: 2026-01-01
- yuen.sha256: c2a9ce966c7e2269

## 法 別表第一 (yuen source)
別表第一
課税物件表（第二条―第五条、第七条、第十二条関係）
課税物件表の適用に関する通則
１
この表における文書の所属の決定は、この表の各号の規定による。この場合において、当該各号の規定により所属を決定することができないときは、２及び３に定めるところによる。
２
一の文書でこの表の二以上の号に掲げる文書により証されるべき事項又はこの表の一若しくは二以上の号に掲げる文書により証されるべき事項とその他の事項とが併記され、又は混合して記載されているものその他一の文書でこれに記載されている事項がこの表の二以上の号に掲げる文書により証されるべき事項に該当するものは、当該各号に掲げる文書に該当する文書とする。
３
一の文書が２の規定によりこの表の各号のうち二以上の号に掲げる文書に該当することとなる場合には、次に定めるところによりその所属を決定する。
イ
第一号又は第二号に掲げる文書と第三号から第十七号までに掲げる文書とに該当する文書は、第一号又は第二号に掲げる文書とする。ただし、第一号又は第二号に掲げる文書で契約金額の記載のないものと第七号に掲げる文書とに該当する文書は、同号に掲げる文書とし、第一号又は第二号に掲げる文書と第十七号に掲げる文書とに該当する文書のうち、当該文書に売上代金（同号の定義の欄１に規定する売上代金をいう。以下この通則において同じ。）に係る受取金額（百万円を超えるものに限る。）の記載があるもので、当該受取金額が当該文書に記載された契約金額（当該金額が二以上ある場合には、その合計額）を超えるもの又は契約金額の記載のないものは、同号に掲げる文書とする。
ロ
第一号に掲げる文書と第二号に掲げる文書とに該当する文書は、第一号に掲げる文書とする。ただし、当該文書に契約金額の記載があり、かつ、当該契約金額を第一号及び第二号に掲げる文書のそれぞれにより証されるべき事項ごとに区分することができる場合において、第一号に掲げる文書により証されるべき事項に係る金額として記載されている契約金額（当該金額が二以上ある場合には、その合計額。以下このロにおいて同じ。）が第二号に掲げる文書により証されるべき事項に係る金額として記載されている契約金額に満たないときは、同号に掲げる文書とする。
ハ
第三号から第十七号までに掲げる文書のうち二以上の号に掲げる文書に該当する文書は、当該二以上の号のうち最も号数の少ない号に掲げる文書とする。ただし、当該文書に売上代金に係る受取金額（百万円を超えるものに限る。）の記載があるときは、第十七号に掲げる文書とする。
ニ
ホに規定する場合を除くほか、第十八号から第二十号までに掲げる文書と第一号から第十七号までに掲げる文書とに該当する文書は、第十八号から第二十号までに掲げる文書とする。
ホ
第十九号若しくは第二十号に掲げる文書と第一号に掲げる文書とに該当する文書で同号に掲げる文書に係る記載された契約金額が十万円を超えるもの、第十九号若しくは第二十号に掲げる文書と第二号に掲げる文書とに該当する文書で同号に掲げる文書に係る記載された契約金額が百万円を超えるもの又は第十九号若しくは第二十号に掲げる文書と第十七号に掲げる文書とに該当する文書で同号に掲げる文書に係る記載された売上代金に係る受取金額が百万円を超えるものは、それぞれ、第一号、第二号又は第十七号に掲げる文書とする。
４
この表の課税標準及び税率の欄の税率又は非課税物件の欄の金額が契約金額、券面金額その他当該文書により証されるべき事項に係る金額（以下この４において「契約金額等」という。）として当該文書に記載された金額（以下この４において「記載金額」という。）を基礎として定められている場合における当該金額の計算については、次に定めるところによる。
イ
当該文書に二以上の記載金額があり、かつ、これらの金額が同一の号に該当する文書により証されるべき事項に係るものである場合には、これらの金額の合計額を当該文書の記載金額とする。
ロ
当該文書が２の規定によりこの表の二以上の号に該当する文書である場合には、次に定めるところによる。
（一）
当該文書の記載金額を当該二以上の号のそれぞれに掲げる文書により証されるべき事項ごとに区分することができるときは、当該文書が３の規定によりこの表のいずれの号に掲げる文書に所属することとなるかに応じ、その所属する号に掲げる文書により証されるべき事項に係る金額を当該文書の記載金額とする。
（二）
当該文書の記載金額を当該二以上の号のそれぞれに掲げる文書により証されるべき事項ごとに区分することができないときは、当該金額（当該金額のうちに、当該文書が３の規定によりこの表のいずれかの号に所属することとなる場合における当該所属する号に掲げる文書により証されるべき事項に係る金額以外の金額として明らかにされている部分があるときは、当該明らかにされている部分の金額を除く。）を当該文書の記載金額とする。
ハ
当該文書が第十七号に掲げる文書（３の規定により同号に掲げる文書となるものを含む。）のうち同号の物件名の欄１に掲げる受取書である場合には、税率の適用に関しては、イ又はロの規定にかかわらず、次に定めるところによる。
（一）
当該受取書の記載金額を売上代金に係る金額とその他の金額に区分することができるときは、売上代金に係る金額を当該受取書の記載金額とする。
（二）
当該受取書の記載金額を売上代金に係る金額とその他の金額に区分することができないときは、当該記載金額（当該金額のうちに売上代金に係る金額以外の金額として明らかにされている部分があるときは、当該明らかにされている部分の金額を除く。）を当該受取書の記載金額とする。
ニ
契約金額等の変更の事実を証すべき文書について、当該文書に係る契約についての変更前の契約金額等の記載のある文書が作成されていることが明らかであり、かつ、変更の事実を証すべき文書により変更金額（変更前の契約金額等と変更後の契約金額等の差額に相当する金額をいう。以下同じ。）が記載されている場合（変更前の契約金額等と変更後の契約金額等が記載されていることにより変更金額を明らかにすることができる場合を含む。）には、当該変更金額が変更前の契約金額等を増加させるものであるときは、当該変更金額を当該文書の記載金額とし、当該変更金額が変更前の契約金額等を減少させるものであるときは、当該文書の記載金額の記載はないものとする。
ホ
次の（一）から（三）までの規定に該当する文書の記載金額については、それぞれ（一）から（三）までに定めるところによる。
（一）
当該文書に記載されている単価及び数量、記号その他によりその契約金額等の計算をすることができるときは、その計算により算出した金額を当該文書の記載金額とする。
（二）
第一号又は第二号に掲げる文書に当該文書に係る契約についての契約金額又は単価、数量、記号その他の記載のある見積書、注文書その他これらに類する文書（この表に掲げる文書を除く。）の名称、発行の日、記号、番号その他の記載があることにより、当事者間において当該契約についての契約金額が明らかであるとき又は当該契約についての契約金額の計算をすることができるときは、当該明らかである契約金額又は当該計算により算出した契約金額を当該第一号又は第二号に掲げる文書の記載金額とする。
（三）
第十七号に掲げる文書のうち売上代金として受け取る有価証券の受取書に当該有価証券の発行者の名称、発行の日、記号、番号その他の記載があること、又は同号に掲げる文書のうち売上代金として受け取る金銭若しくは有価証券の受取書に当該売上代金に係る受取金額の記載のある支払通知書、請求書その他これらに類する文書の名称、発行の日、記号、番号その他の記載があることにより、当事者間において当該売上代金に係る受取金額が明らかであるときは、当該明らかである受取金額を当該受取書の記載金額とする。
ヘ
当該文書の記載金額が外国通貨により表示されている場合には、当該文書を作成した日における外国為替及び外国貿易法（昭和二十四年法律第二百二十八号）第七条第一項（外国為替相場）の規定により財務大臣が定めた基準外国為替相場又は裁定外国為替相場により当該記載金額を本邦通貨に換算した金額を当該文書についての記載金額とする。
５
この表の第一号、第二号、第七号及び第十二号から第十五号までにおいて「契約書」とは、契約証書、協定書、約定書その他名称のいかんを問わず、契約（その予約を含む。以下同じ。）の成立若しくは更改又は契約の内容の変更若しくは補充の事実（以下「契約の成立等」という。）を証すべき文書をいい、念書、請書その他契約の当事者の一方のみが作成する文書又は契約の当事者の全部若しくは一部の署名を欠く文書で、当事者間の了解又は商慣習に基づき契約の成立等を証することとされているものを含むものとする。
６ １から５までに規定するもののほか、この表の規定の適用に関し必要な事項は、政令で定める。
番号
課税物件
課税標準及び税率
非課税物件
物件名
定義
一
１ 不動産、鉱業権、貯留権、二酸化炭素の貯留事業に関する法律（令和六年法律第三十八号）第二条第八項（定義）に規定する試掘権、無体財産権、船舶若しくは航空機又は営業の譲渡に関する契約書
２ 地上権又は土地の賃借権の設定又は譲渡に関する契約書
３ 消費貸借に関する契約書
４ 運送に関する契約書（傭よう船契約書を含む。）
１ 不動産には、法律の規定により不動産とみなされるもののほか、鉄道財団、軌道財団及び自動車交通事業財団を含むものとする。
２ 無体財産権とは、特許権、実用新案権、商標権、意匠権、回路配置利用権、育成者権、商号及び著作権をいう。
３ 運送に関する契約書には、乗車券、乗船券、航空券及び送り状を含まないものとする。
４ 傭船契約書には、航空機の傭船契約書を含むものとし、裸傭船契約書を含まないものとする。
１ 契約金額の記載のある契約書
次に掲げる契約金額の区分に応じ、一通につき、次に掲げる税率とする。
十万円以下のもの 二百円
十万円を超え五十万円以下のもの 四百円
五十万円を超え百万円以下のもの 千円
百万円を超え五百万円以下のもの 二千円
五百万円を超え千万円以下のもの 一万円
千万円を超え五千万円以下のもの 二万円
五千万円を超え一億円以下のもの 六万円
一億円を超え五億円以下のもの 十万円
五億円を超え十億円以下のもの 二十万円
十億円を超え五十億円以下のもの 四十万円
五十億円を超えるもの 六十万円
２ 契約金額の記載のない契約書
一通につき 二百円
１ 契約金額の記載のある契約書（課税物件表の適用に関する通則３イの規定が適用されることによりこの号に掲げる文書となるものを除く。）のうち、当該契約金額が一万円未満のもの
二
請負に関する契約書
１ 請負には、職業野球の選手、映画の俳優その他これらに類する者で政令で定めるものの役務の提供を約することを内容とする契約を含むものとする。
１ 契約金額の記載のある契約書
次に掲げる契約金額の区分に応じ、一通につき、次に掲げる税率とする。
百万円以下のもの 二百円
百万円を超え二百万円以下のもの 四百円
二百万円を超え三百万円以下のもの 千円
三百万円を超え五百万円以下のもの 二千円
五百万円を超え千万円以下のもの 一万円
千万円を超え五千万円以下のもの 二万円
五千万円を超え一億円以下のもの 六万円
一億円を超え五億円以下のもの 十万円
五億円を超え十億円以下のもの 二十万円
十億円を超え五十億円以下のもの 四十万円
五十億円を超えるもの 六十万円
２ 契約金額の記載のない契約書
一通につき 二百円
１ 契約金額の記載のある契約書（課税物件表の適用に関する通則３イの規定が適用されることによりこの号に掲げる文書となるものを除く。）のうち、当該契約金額が一万円未満のもの
三
約束手形又は為替手形
１ ２に掲げる手形以外の手形
次に掲げる手形金額の区分に応じ、一通につき、次に掲げる税率とする。
百万円以下のもの 二百円
百万円を超え二百万円以下のもの 四百円
二百万円を超え三百万円以下のもの 六百円
三百万円を超え五百万円以下のもの 千円
五百万円を超え千万円以下のもの 二千円
千万円を超え二千万円以下のもの 四千円
二千万円を超え三千万円以下のもの 六千円
三千万円を超え五千万円以下のもの 一万円
五千万円を超え一億円以下のもの 二万円
一億円を超え二億円以下のもの 四万円
二億円を超え三億円以下のもの 六万円
三億円を超え五億円以下のもの 十万円
五億円を超え十億円以下のもの 十五万円
十億円を超えるもの 二十万円
１ 手形金額が十万円未満の手形
２ 手形金額の記載のない手形
３ 手形の複本又は謄本
２ 次に掲げる手形
一通につき 二百円
イ 一覧払の手形（手形法（昭和七年法律第二十号）第三十四条第二項（一覧払の為替手形の呈示開始期日の定め）（同法第七十七条第一項第二号（約束手形への準用）において準用する場合を含む。）の定めをするものを除く。）
ロ 日本銀行又は銀行その他政令で定める金融機関を振出人及び受取人とする手形（振出人である銀行その他当該政令で定める金融機関を受取人とするものを除く。）
ハ 外国通貨により手形金額が表示される手形
ニ 外国為替及び外国貿易法第六条第一項第六号（定義）に規定する非居住者の本邦にある同法第十六条の二（支払等の制限）に規定する銀行等（以下この号において「銀行等」という。）に対する本邦通貨をもつて表示される勘定を通ずる方法により決済される手形で政令で定めるもの
ホ 本邦から貨物を輸出し又は本邦に貨物を輸入する外国為替及び外国貿易法第六条第一項第五号（定義）に規定する居住者が本邦にある銀行等を支払人として振り出す本邦通貨により手形金額が表示される手形で政令で定めるもの
ヘ ホに掲げる手形及び外国の法令に準拠して外国において銀行業を営む者が本邦にある銀行等を支払人として振り出した本邦通貨により手形金額が表示される手形で政令で定めるものを担保として、銀行等が自己を支払人として振り出す本邦通貨により手形金額が表示される手形で政令で定めるもの
四
株券、出資証券若しくは社債券又は投資信託、貸付信託、特定目的信託若しくは受益証券発行信託の受益証券
１ 出資証券とは、相互会社（保険業法（平成七年法律第百五号）第二条第五項（定義）に規定する相互会社をいう。以下同じ。）の作成する基金証券及び法人の社員又は出資者たる地位を証する文書（投資信託及び投資法人に関する法律（昭和二十六年法律第百九十八号）に規定する投資証券を含む。）をいう。
２ 社債券には、特別の法律により法人の発行する債券及び相互会社の社債券を含むものとする。
次に掲げる券面金額（券面金額の記載のない証券で株数又は口数の記載のあるものにあつては、一株又は一口につき政令で定める金額に当該株数又は口数を乗じて計算した金額）の区分に応じ、一通につき、次に掲げる税率とする。
五百万円以下のもの 二百円
五百万円を超え千万円以下のもの 千円
千万円を超え五千万円以下のもの 二千円
五千万円を超え一億円以下のもの 一万円
一億円を超えるもの 二万円
１ 日本銀行その他特別の法律により設立された法人で政令で定めるものの作成する出資証券（協同組織金融機関の優先出資に関する法律（平成五年法律第四十四号）に規定する優先出資証券を除く。）
２ 受益権を他の投資信託の受託者に取得させることを目的とする投資信託の受益証券で政令で定めるもの
五
合併契約書又は吸収分割契約書若しくは新設分割計画書
１ 合併契約書とは、会社法（平成十七年法律第八十六号）第七百四十八条（合併契約の締結）に規定する合併契約（保険業法第百五十九条第一項（相互会社と株式会社の合併）に規定する合併契約を含む。）を証する文書（当該合併契約の変更又は補充の事実を証するものを含む。）をいう。
２ 吸収分割契約書とは、会社法第七百五十七条（吸収分割契約の締結）に規定する吸収分割契約を証する文書（当該吸収分割契約の変更又は補充の事実を証するものを含む。）をいう。
３ 新設分割計画書とは、会社法第七百六十二条第一項（新設分割計画の作成）に規定する新設分割計画を証する文書（当該新設分割計画の変更又は補充の事実を証するものを含む。）をいう。
一通につき 四万円
六
定款
１ 定款は、会社（相互会社を含む。）の設立のときに作成される定款の原本に限るものとする。
一通につき 四万円
１ 株式会社又は相互会社の定款のうち、公証人法第五十八条第三項（書面の定款の認証）の規定により公証人の保存するもの以外のもの
七
継続的取引の基本となる契約書（契約期間の記載のあるもののうち、当該契約期間が三月以内であり、かつ、更新に関する定めのないものを除く。）
１ 継続的取引の基本となる契約書とは、特約店契約書、代理店契約書、銀行取引約定書その他の契約書で、特定の相手方との間に継続的に生ずる取引の基本となるもののうち、政令で定めるものをいう。
一通につき 四千円
八
預貯金証書
一通につき 二百円
１ 信用金庫その他政令で定める金融機関の作成する預貯金証書で、記載された預入額が一万円未満のもの
九
倉荷証券、船荷証券又は複合運送証券
１ 倉荷証券には、商法（明治三十二年法律第四十八号）第六百一条（倉荷証券の記載事項）の記載事項の一部を欠く証書で、倉荷証券と類似の効用を有するものを含むものとする。
２ 船荷証券又は複合運送証券には、商法第七百五十八条（船荷証券の記載事項）（同法第七百六十九条第二項（複合運送証券）において準用する場合を含む。）の記載事項の一部を欠く証書で、これらの証券と類似の効用を有するものを含むものとする。
一通につき 二百円
十
保険証券
１ 保険証券とは、保険証券その他名称のいかんを問わず、保険法（平成二十年法律第五十六号）第六条第一項（損害保険契約の締結時の書面交付）、第四十条第一項（生命保険契約の締結時の書面交付）又は第六十九条第一項（傷害疾病定額保険契約の締結時の書面交付）その他の法令の規定により、保険契約に係る保険者が当該保険契約を締結したときに当該保険契約に係る保険契約者に対して交付する書面（当該保険契約者からの再交付の請求により交付するものを含み、保険業法第三条第五項第三号（免許）に掲げる保険に係る保険契約その他政令で定める保険契約に係るものを除く。）をいう。
一通につき 二百円
十一
信用状
一通につき 二百円
十二
信託行為に関する契約書
１ 信託行為に関する契約書には、信託証書を含むものとする。
一通につき 二百円
１ 公益信託に関する法律（令和六年法律第三十号）第二条第一項第一号（定義）に規定する公益信託の信託行為に関する契約書（同法第六条（公益信託の効力）の規定による行政庁の認可又は同法第二十二条第一項（公益信託の併合等の認可）の規定による行政庁の認可（併合に係るものに限る。）を受けた後に作成されるものに限る。）
十三
債務の保証に関する契約書（主たる債務の契約書に併記するものを除く。）
一通につき 二百円
１ 身元保証ニ関スル法律（昭和八年法律第四十二号）に定める身元保証に関する契約書
十四
金銭又は有価証券の寄託に関する契約書
一通につき 二百円
十五
債権譲渡又は債務引受けに関する契約書
一通につき 二百円
１ 契約金額の記載のある契約書のうち、当該契約金額が一万円未満のもの
十六
配当金領収証又は配当金振込通知書
１ 配当金領収証とは、配当金領収書その他名称のいかんを問わず、配当金の支払を受ける権利を表彰する証書又は配当金の受領の事実を証するための証書をいう。
２ 配当金振込通知書とは、配当金振込票その他名称のいかんを問わず、配当金が銀行その他の金融機関にある株主の預貯金口座その他の勘定に振込済みである旨を株主に通知する文書をいう。
一通につき 二百円
１ 記載された配当金額が三千円未満の証書又は文書
十七
１ 売上代金に係る金銭又は有価証券の受取書
２ 金銭又は有価証券の受取書で１に掲げる受取書以外のもの
１ 売上代金に係る金銭又は有価証券の受取書とは、資産を譲渡し若しくは使用させること（当該資産に係る権利を設定することを含む。）又は役務を提供することによる対価（手付けを含み、金融商品取引法（昭和二十三年法律第二十五号）第二条第一項（定義）に規定する有価証券その他これに準ずるもので政令で定めるものの譲渡の対価、保険料その他政令で定めるものを除く。以下「売上代金」という。）として受け取る金銭又は有価証券の受取書をいい、次に掲げる受取書を含むものとする。
イ 当該受取書に記載されている受取金額の一部に売上代金が含まれている金銭又は有価証券の受取書及び当該受取金額の全部又は一部が売上代金であるかどうかが当該受取書の記載事項により明らかにされていない金銭又は有価証券の受取書
ロ 他人の事務の委託を受けた者（以下この欄において「受託者」という。）が当該委託をした者（以下この欄において「委託者」という。）に代わつて売上代金を受け取る場合に作成する金銭又は有価証券の受取書（銀行その他の金融機関が作成する預貯金口座への振込金の受取書その他これに類するもので政令で定めるものを除く。ニにおいて同じ。）
１ 売上代金に係る金銭又は有価証券の受取書で受取金額の記載のあるもの
次に掲げる受取金額の区分に応じ、一通につき、次に掲げる税率とする。
百万円以下のもの 二百円
百万円を超え二百万円以下のもの 四百円
二百万円を超え三百万円以下のもの 六百円
三百万円を超え五百万円以下のもの 千円
五百万円を超え千万円以下のもの 二千円
千万円を超え二千万円以下のもの 四千円
二千万円を超え三千万円以下のもの 六千円
三千万円を超え五千万円以下のもの 一万円
五千万円を超え一億円以下のもの 二万円
一億円を超え二億円以下のもの 四万円
二億円を超え三億円以下のもの 六万円
三億円を超え五億円以下のもの 十万円
五億円を超え十億円以下のもの 十五万円
十億円を超えるもの 二十万円
２ １に掲げる受取書以外の受取書
一通につき 二百円
１ 記載された受取金額が五万円未満の受取書
２ 営業（会社以外の法人で、法令の規定又は定款の定めにより利益金又は剰余金の配当又は分配をすることができることとなつているものが、その出資者以外の者に対して行う事業を含み、当該出資者がその出資をした法人に対して行う営業を除く。）に関しない受取書
３ 有価証券又は第八号、第十二号、第十四号若しくは前号に掲げる文書に追記した受取書
ハ 受託者が委託者に代わつて受け取る売上代金の全部又は一部に相当する金額を委託者が受託者から受け取る場合に作成する金銭又は有価証券の受取書
ニ 受託者が委託者に代わつて支払う売上代金の全部又は一部に相当する金額を委託者から受け取る場合に作成する金銭又は有価証券の受取書
十八
預貯金通帳、信託行為に関する通帳、銀行若しくは無尽会社の作成する掛金通帳、生命保険会社の作成する保険料通帳又は生命共済の掛金通帳
１ 生命共済の掛金通帳とは、農業協同組合その他の法人が生命共済に係る契約に関し作成する掛金通帳で、政令で定めるものをいう。
一冊につき 二百円
１ 信用金庫その他政令で定める金融機関の作成する預貯金通帳
２ 所得税法第九条第一項第二号（非課税所得）に規定する預貯金に係る預貯金通帳その他政令で定める普通預金通帳
十九
第一号、第二号、第十四号又は第十七号に掲げる文書により証されるべき事項を付け込んで証明する目的をもつて作成する通帳（前号に掲げる通帳を除く。）
一冊につき 四百円
二十
判取帳
１ 判取帳とは、第一号、第二号、第十四号又は第十七号に掲げる文書により証されるべき事項につき二以上の相手方から付込証明を受ける目的をもつて作成する帳簿をいう。
一冊につき 四千円
- yuen.law: egov 342AC0000000023
- yuen.asof: 2026-04-01
- yuen.revision: 342AC0000000023_20260401_507AC0000000052
- yuen.sha256: 0ba69792e960021e

## 措置法 第91条 (yuen source)
（不動産の譲渡に関する契約書等に係る印紙税の税率の特例）
第九十一条 平成二十六年四月一日から令和九年三月三十一日までの間に作成される印紙税法別表第一第一号の物件名の欄１に掲げる不動産の譲渡に関する契約書（一の文書が当該契約書と当該契約書以外の同号に掲げる契約書とに該当する場合における当該一の文書を含む。以下この項及び次条第一項において「不動産譲渡契約書」という。）のうち、当該不動産譲渡契約書に記載された契約金額が十万円を超えるものに係る印紙税の税率は、同号の規定にかかわらず、次の各号に掲げる契約金額の区分に応じ、一通につき、当該各号に定める金額とする。
一 十万円を超え五十万円以下のもの 二百円
二 五十万円を超え百万円以下のもの 五百円
三 百万円を超え五百万円以下のもの 千円
四 五百万円を超え千万円以下のもの 五千円
五 千万円を超え五千万円以下のもの 一万円
六 五千万円を超え一億円以下のもの 三万円
七 一億円を超え五億円以下のもの 六万円
八 五億円を超え十億円以下のもの 十六万円
九 十億円を超え五十億円以下のもの 三十二万円
十 五十億円を超えるもの 四十八万円
２ 平成二十六年四月一日から令和九年三月三十一日までの間に作成される印紙税法別表第一第二号に掲げる請負に関する契約書（建設業法第二条第一項に規定する建設工事の請負に係る契約に基づき作成されるものに限る。以下この項及び次条第一項において「建設工事請負契約書」という。）のうち、当該建設工事請負契約書に記載された契約金額が百万円を超えるものに係る印紙税の税率は、同号の規定にかかわらず、次の各号に掲げる契約金額の区分に応じ、一通につき、当該各号に定める金額とする。
一 百万円を超え二百万円以下のもの 二百円
二 二百万円を超え三百万円以下のもの 五百円
三 三百万円を超え五百万円以下のもの 千円
四 五百万円を超え千万円以下のもの 五千円
五 千万円を超え五千万円以下のもの 一万円
六 五千万円を超え一億円以下のもの 三万円
七 一億円を超え五億円以下のもの 六万円
八 五億円を超え十億円以下のもの 十六万円
九 十億円を超え五十億円以下のもの 三十二万円
十 五十億円を超えるもの 四十八万円
３ 前二項の規定の適用がある場合における印紙税法第四条第四項及び別表第一の課税物件表の適用に関する通則３の規定の適用については、同項第一号中「十万円」とあるのは「十万円（当該課税文書が租税特別措置法（昭和三十二年法律第二十六号）第九十一条第一項に規定する不動産譲渡契約書である場合にあつては、五十万円）」と、同項第二号中「百万円」とあるのは「百万円（当該課税文書が租税特別措置法第九十一条第二項に規定する建設工事請負契約書である場合にあつては、二百万円）」と、同法別表第一の課税物件表の適用に関する通則３ホ中「十万円」とあるのは「十万円（同号に掲げる文書が租税特別措置法第九十一条第一項に規定する不動産譲渡契約書である場合にあつては、五十万円）」と、「契約金額が百万円」とあるのは「契約金額が百万円（同号に掲げる文書が同条第二項に規定する建設工事請負契約書である場合にあつては、二百万円）」とする。
- yuen.law: egov 332AC0000000026
- yuen.asof: 2026-04-01
- yuen.revision: 332AC0000000026_20260401_508AC0000000012
- yuen.sha256: 85faf53f6f6e8196

# Specification: artifacts

## rulec "rules/osha_extinguisher.rule" table distance (yuen artifact)
- yuen.sha256: 5681500476af8a56
- yuen.end: item

## rulec "rules/印紙税の本則と軽減.rule" table 本則 (yuen artifact)
- yuen.sha256: 21432c19a67fe72e
- yuen.end: item

## rulec "rules/印紙税の本則と軽減.rule" clause 非課税 (yuen artifact)
- yuen.sha256: 5bc61581e0c31022
- yuen.end: item

## rulec "rules/印紙税の本則と軽減.rule" table 軽減 (yuen artifact)
- yuen.sha256: 4ba4c2dec2c8262b
- yuen.end: item

## rulec "rules/印紙税の本則と軽減.rule" define 軽減期間 (yuen artifact)
- yuen.sha256: b5b30cefd66e58d6
- yuen.end: item
