# ordering_terms

# Specification: ordering_terms
- yuen.file: ordering_terms.req
- yuen.version: 1
- yuen.description: A test material: the words of the context ordering.ctx of sakai's example, named by where in the glossary they come from

## order v1: order (yuen requirement)
An order is a purchase the customer has confirmed, and it does not disappear when it is cancelled
- yuen.owner: ordering
- yuen.waived: not verified "This material has no claim that checks how the word is used"
  approved 2026-10-04 by ordering sha256:419ff25fab796bd2
- yuen.sha256: 419ff25fab796bd2
- yuen.status: ok
- yuen from -> glossary
- yuen satisfied by -> sakai "contexts/ordering.ctx" term order

## cancel v1: cancel (yuen requirement)
Cancel is cancelling an order before it ships, at the customer's request
- yuen.owner: ordering
- yuen.waived: not verified "This material has no claim that checks how the word is used"
  approved 2026-10-04 by ordering sha256:9937cc2b5ce6aa4b
- yuen.sha256: 9937cc2b5ce6aa4b
- yuen.status: ok
- yuen from -> glossary
- yuen satisfied by -> sakai "contexts/ordering.ctx" term cancel

# Specification: sources

## glossary (yuen source)
- yuen.file: glossary.md
- yuen.sha256: cb130a5f6f2a81ec

# Specification: artifacts

## sakai "contexts/ordering.ctx" term order (yuen artifact)
- yuen.sha256: 299fcb6a6845f6af
- yuen.end: item

## sakai "contexts/ordering.ctx" term cancel (yuen artifact)
- yuen.sha256: 4687c56296431a6b
- yuen.end: item
