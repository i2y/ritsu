# 返金

# Specification: 返金
- yuen.file: 返金.req
- yuen.version: 1
- yuen.description: chobo の例「refunds.ja.book」の勘定と振替が、返金の方針のどこから来たかを書いたテストの材料。出典は方針の文書を保存して固定し、成果物は勘定と振替を一つずつ指す

## within_sales v1: 売上を超えない (yuen requirement)
返金は、その注文の売上を超えない
- yuen.inForce: 2026-10-01..
- yuen.owner: 経理
- yuen.waived: not verified "残りが 0 より下にならないことは chobo の検査が確かめる。この材料は、それを指す主張を持たない"
  approved 2026-10-04 by 経理 sha256:7c5b2a8cb5f9eb15
- yuen.sha256: 7c5b2a8cb5f9eb15
- yuen.status: ok
- yuen from -> 方針
- yuen satisfied by -> chobo "refunds.ja.book" account 返金できる残り
- yuen satisfied by -> chobo "refunds.ja.book" transfer 売上計上

## hold_until_approved v1: 承認まで押さえる (yuen requirement)
返金は、担当者が承認するまで確定しない。承認を待つあいだ、その額を押さえる
- yuen.inForce: 2026-10-01..
- yuen.owner: 経理
- yuen.waived: not verified "押さえた額が期限で戻ることは chobo のシナリオが確かめる。この材料は、それを指す主張を持たない"
  approved 2026-10-04 by 経理 sha256:b13e498e17a4fd86
- yuen.sha256: b13e498e17a4fd86
- yuen.status: ok
- yuen from -> 方針
- yuen satisfied by -> chobo "refunds.ja.book" transfer 返金

## record_together v1: まとめて記録する (yuen requirement)
返金した額は、注文ごとではなく、まとめて記録する
- yuen.inForce: 2026-10-01..
- yuen.owner: 経理
- yuen.waived: not verified "この材料は、それを確かめる主張を持たない"
  approved 2026-10-04 by 経理 sha256:fe6a4543a7261757
- yuen.sha256: fe6a4543a7261757
- yuen.status: ok
- yuen from -> 方針
- yuen satisfied by -> chobo "refunds.ja.book" account 返金済み

# Specification: sources

## 方針 (yuen source)
- yuen.file: 返金の方針.md
- yuen.sha256: 4a847d6d9b3e4853

# Specification: artifacts

## chobo "refunds.ja.book" account 返金できる残り (yuen artifact)
- yuen.sha256: 9f9b0d74872f62a4
- yuen.end: item

## chobo "refunds.ja.book" transfer 売上計上 (yuen artifact)
- yuen.sha256: 851ab806078168fe
- yuen.end: item

## chobo "refunds.ja.book" transfer 返金 (yuen artifact)
- yuen.sha256: 84e9ce254075c697
- yuen.end: item

## chobo "refunds.ja.book" account 返金済み (yuen artifact)
- yuen.sha256: 35a4ec5a2ee5eb06
- yuen.end: item
