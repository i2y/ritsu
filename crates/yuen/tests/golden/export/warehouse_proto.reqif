# inventory

# Specification: inventory
- yuen.file: inventory.req
- yuen.version: 1
- yuen.description: A test material: the promises of the warehouse and shipping services of dandori's example fulfillment, named by elements of the .proto files. The source is a copy of the document of the promises, pinned

## reserve v1: reserve (yuen requirement)
The warehouse holds stock for each line of an order. When there is not enough, it answers so without holding any
- yuen.owner: warehouse
- yuen.waived: not verified "This material has no claim that runs the service"
  approved 2026-10-04 by warehouse sha256:054a0be4bb4bbe79
- yuen.sha256: 054a0be4bb4bbe79
- yuen.status: ok
- yuen from -> contract
- yuen satisfied by -> proto "warehouse.proto" service StockService method Reserve
- yuen satisfied by -> proto "warehouse.proto" enum Stock

## release v1: release (yuen requirement)
Stock held is released with the number it was held with
- yuen.owner: warehouse
- yuen.waived: not verified "This material has no claim that runs the service"
  approved 2026-10-04 by warehouse sha256:870d0744de8ff13a
- yuen.sha256: 870d0744de8ff13a
- yuen.status: ok
- yuen from -> contract
- yuen satisfied by -> proto "warehouse.proto" service StockService method Release

## fulfill v1: fulfill (yuen requirement)
Fulfillment starts with an order, and answers with the stock held and a tracking number
- yuen.owner: warehouse
- yuen.waived: not verified "This material has no claim that runs the service"
  approved 2026-10-04 by warehouse sha256:83acaba766b0b3b5
- yuen.sha256: 83acaba766b0b3b5
- yuen.status: ok
- yuen from -> contract
- yuen satisfied by -> proto "fulfillment.proto" service FulfillmentService method Fulfill
- yuen satisfied by -> proto "fulfillment.proto" message FulfillResponse field tracking_number

# Specification: sources

## contract (yuen source)
- yuen.file: contract.md
- yuen.sha256: 997c973ba5bd5798

# Specification: artifacts

## proto "warehouse.proto" service StockService method Reserve (yuen artifact)
- yuen.sha256: cadb2fc727e9af81
- yuen.end: item

## proto "warehouse.proto" enum Stock (yuen artifact)
- yuen.sha256: d7450e7503c905f7
- yuen.end: item

## proto "warehouse.proto" service StockService method Release (yuen artifact)
- yuen.sha256: 2a0912a66889e515
- yuen.end: item

## proto "fulfillment.proto" service FulfillmentService method Fulfill (yuen artifact)
- yuen.sha256: 6c73e17bf5bedba7
- yuen.end: item

## proto "fulfillment.proto" message FulfillResponse field tracking_number (yuen artifact)
- yuen.sha256: fb7f7e2617539e54
- yuen.end: item
