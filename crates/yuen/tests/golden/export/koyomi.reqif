# 支払条件, 民法の期間

# Specification: 支払条件
- yuen.file: 支払条件.req
- yuen.version: 1
- yuen.description: koyomi の例「支払_20日締め翌月10日払い.cal」の支払日を書いたテストの材料。休みの日の出典は、カレンダーのファイルが固定している祝日の表を借りる。支払の条件は、この材料のために書いたもの

## payment_day v1: 支払日 (yuen requirement)
20 日締め翌月 10 日払い。支払日が休みなら、その前の営業日に払う
- yuen.inForce: 2026-10-01..
- yuen.owner: 経理
- yuen.sha256: 870271e179a7d233
- yuen.status: ok
- yuen from -> 祝日
- yuen satisfied by -> koyomi "支払_20日締め翌月10日払い.cal" date 支払日
- yuen verified by -> koyomi "支払_20日締め翌月10日払い.cal" claim 営業日に払う

# Specification: 民法の期間
- yuen.file: 民法の期間.req
- yuen.version: 1
- yuen.description: koyomi の例「民法の期間.cal」の日付と条件が、民法のどの条から来たかを書いたテストの材料。出典は koyomi のファイルが固定しているものを借り、成果物は日付と条件を一つずつ指す。例として書いたもので、法令の読み方を示すものではない

## first_day v1: 起算日 (yuen requirement)
日、週、月又は年によって期間を定めたときは、期間の初日は、算入しない。ただし、その期間が午前零時から始まるときは、この限りでない
- yuen.inForce: 2026-10-01..
- yuen.owner: 法務
- yuen.waived: not verified "初日を算入しないことは、koyomi doc のページで、条文と言い直しを見比べて確かめる。この材料に、それを確かめる条件は無い"
  approved 2026-10-04 by 法務 sha256:a9ebc73907faddc8
- yuen.sha256: a9ebc73907faddc8
- yuen.status: ok
- yuen from -> 民法 第140条
- yuen satisfied by -> koyomi "民法の期間.cal" date 起算日

## last_day v1: 満了日 (yuen requirement)
月によって期間を定めたときは、最後の月においてその起算日に応当する日の前日の終わりに満了する。応当する日がないときは、その月の末日の終わりに満了する
- yuen.inForce: 2026-10-01..
- yuen.owner: 法務
- yuen.sha256: 465b83ed8c251406
- yuen.status: ok
- yuen from -> 民法 第141条
- yuen from -> 民法 第143条
- yuen satisfied by -> koyomi "民法の期間.cal" date 満了日
- yuen verified by -> koyomi "民法の期間.cal" claim 満了日は起点より後

## last_day_142 v1: 満了日_142条 (yuen requirement)
期間の末日が日曜日、国民の祝日に関する法律に規定する休日その他の休日に当たるときは、その日に取引をしない慣習がある場合に限り、期間は、その翌日に満了する
- yuen.inForce: 2026-10-01..
- yuen.owner: 法務
- yuen.decided: decided 2026-10-03 by 法務 "「その翌日」は文字どおり末日の翌日と読み、翌日も休みでもそれ以上は動かさない。この材料のために決めたもので、法令の読み方を示すものではない"
- yuen.sha256: d4f2d2a67322df17
- yuen.status: ok
- yuen from -> 民法 第142条
- yuen satisfied by -> koyomi "民法の期間.cal" date 満了日_142条
- yuen verified by -> koyomi "民法の期間.cal" claim 142条の満了日は満了日以後

# Specification: sources

## 祝日 (yuen source)
- yuen.file: calendars/data/syukujitsu.csv
- yuen.url: https://www8.cao.go.jp/chosei/shukujitsu/syukujitsu.csv
- yuen.sha256: cec37a743c96995c

## 民法 第140条 (yuen source)
第百四十条 日、週、月又は年によって期間を定めたときは、期間の初日は、算入しない。ただし、その期間が午前零時から始まるときは、この限りでない。
- yuen.law: egov 129AC0000000089
- yuen.asof: 2026-10-01
- yuen.revision: 129AC0000000089_20260624_508AC0000000045
- yuen.sha256: e880059021fbb67d

## 民法 第141条 (yuen source)
（期間の満了）
第百四十一条 前条の場合には、期間は、その末日の終了をもって満了する。
- yuen.law: egov 129AC0000000089
- yuen.asof: 2026-10-01
- yuen.revision: 129AC0000000089_20260624_508AC0000000045
- yuen.sha256: 0575c131b9f08063

## 民法 第142条 (yuen source)
第百四十二条 期間の末日が日曜日、国民の祝日に関する法律（昭和二十三年法律第百七十八号）に規定する休日その他の休日に当たるときは、その日に取引をしない慣習がある場合に限り、期間は、その翌日に満了する。
- yuen.law: egov 129AC0000000089
- yuen.asof: 2026-10-01
- yuen.revision: 129AC0000000089_20260624_508AC0000000045
- yuen.sha256: fc8c35a0769d3b35

## 民法 第143条 (yuen source)
（暦による期間の計算）
第百四十三条 週、月又は年によって期間を定めたときは、その期間は、暦に従って計算する。
２ 週、月又は年の初めから期間を起算しないときは、その期間は、最後の週、月又は年においてその起算日に応当する日の前日に満了する。ただし、月又は年によって期間を定めた場合において、最後の月に応当する日がないときは、その月の末日に満了する。
- yuen.law: egov 129AC0000000089
- yuen.asof: 2026-10-01
- yuen.revision: 129AC0000000089_20260624_508AC0000000045
- yuen.sha256: 6950bdfb988439b6

# Specification: artifacts

## koyomi "支払_20日締め翌月10日払い.cal" date 支払日 (yuen artifact)
- yuen.sha256: feb9535fb9350ecc
- yuen.end: item

## koyomi "支払_20日締め翌月10日払い.cal" claim 営業日に払う (yuen artifact)
- yuen.sha256: 3cf8fc3fb2dda9d9
- yuen.end: item

## koyomi "民法の期間.cal" date 起算日 (yuen artifact)
- yuen.sha256: 15aa6c91d6aaae80
- yuen.end: item

## koyomi "民法の期間.cal" date 満了日 (yuen artifact)
- yuen.sha256: 23441fd408f07548
- yuen.end: item

## koyomi "民法の期間.cal" claim 満了日は起点より後 (yuen artifact)
- yuen.sha256: 5e7bb0ed51835dc7
- yuen.end: item

## koyomi "民法の期間.cal" date 満了日_142条 (yuen artifact)
- yuen.sha256: bba4761410179e6e
- yuen.end: item

## koyomi "民法の期間.cal" claim 142条の満了日は満了日以後 (yuen artifact)
- yuen.sha256: 7c616f5dcc9503a8
- yuen.end: item
