# 配送

# Specification: 配送
- yuen.file: 配送.req
- yuen.version: 1
- yuen.description: dandori の例「arrange_delivery.ja.flow」のタスクとレコードが、配送の手順のどこから来たかを書いたテストの材料

## next_day v1: 翌日便 (yuen requirement)
翌日便は運送会社に集荷を頼む。車が空いていなければ、そう言って止める
- yuen.owner: 物流
- yuen.waived: not verified "この材料は、ワークフローを走らせる主張を持たない"
  approved 2026-10-04 by 物流 sha256:14807ac1afa3333a
- yuen.sha256: 14807ac1afa3333a
- yuen.status: ok
- yuen from -> 手順
- yuen satisfied by -> dandori "arrange_delivery.ja.flow" task 翌日便を頼む

## regular v1: 通常便 (yuen requirement)
通常便は郵便に小包を頼む
- yuen.owner: 物流
- yuen.waived: not verified "この材料は、ワークフローを走らせる主張を持たない"
  approved 2026-10-04 by 物流 sha256:907ce7d3f631812e
- yuen.sha256: 907ce7d3f631812e
- yuen.status: ok
- yuen from -> 手順
- yuen satisfied by -> dandori "arrange_delivery.ja.flow" task 通常便を頼む

## tracking_number v1: 追跡番号 (yuen requirement)
どちらの便でも、追跡番号を返す
- yuen.owner: 物流
- yuen.waived: not verified "この材料は、ワークフローを走らせる主張を持たない"
  approved 2026-10-04 by 物流 sha256:6fc243c572acc9d4
- yuen.sha256: 6fc243c572acc9d4
- yuen.status: ok
- yuen from -> 手順
- yuen satisfied by -> dandori "arrange_delivery.ja.flow" record 集荷 field 追跡番号
- yuen satisfied by -> dandori "arrange_delivery.ja.flow" output 追跡番号

# Specification: sources

## 手順 (yuen source)
- yuen.file: 配送の手順.md
- yuen.sha256: b3d6f4b8ced5716c

# Specification: artifacts

## dandori "arrange_delivery.ja.flow" task 翌日便を頼む (yuen artifact)
- yuen.sha256: 3c19313a3f633021
- yuen.end: item

## dandori "arrange_delivery.ja.flow" task 通常便を頼む (yuen artifact)
- yuen.sha256: fb518dde20b90816
- yuen.end: item

## dandori "arrange_delivery.ja.flow" record 集荷 field 追跡番号 (yuen artifact)
- yuen.sha256: 69aa90b09002e1fc
- yuen.end: item

## dandori "arrange_delivery.ja.flow" output 追跡番号 (yuen artifact)
- yuen.sha256: 69aa90b09002e1fc
- yuen.end: item
