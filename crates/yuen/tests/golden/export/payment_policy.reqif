# payment_terms, payment_policy

# Specification: payment_terms
- yuen.file: payment.req
- yuen.version: 1
- yuen.description: A test material: a requirement with two versions, a replacement, and a requirement read from one of another file. The terms are decided for the example; they are not real payment terms

## month_end_close v1: month_end_close (yuen requirement)
Invoices close at the end of the month
- yuen.inForce: 2026-01-01..2027-03-31
- yuen.owner: accounting
- yuen.decided: decided 2025-12-01 by accounting "Closing is made the end of the month. Decided for this material"
- yuen.waived: not verified "The closing day only returns the last date of the month, so no claim is set to check it"
  approved 2026-10-03 by accounting sha256:57e93b89b6e853e5
- yuen.sha256: 57e93b89b6e853e5
- yuen.status: ok
- yuen satisfied by -> file "src/close.py"

## payment_day v1 (yuen requirement)
Closes at the end of the month, pays at the end of the next month
- yuen.inForce: 2026-01-01..2027-03-31
- yuen.owner: accounting
- yuen.sha256: d78a1ef755846010
- yuen.status: ok
- yuen from -> payment_policy v1
- yuen satisfied by -> file "src/pay.py"
- yuen verified by -> file "tests/test_pay.py"

## payment_day v2 (yuen requirement)
Closes on the 20th, pays on the 10th of the next month
- yuen.inForce: 2027-04-01..
- yuen.owner: accounting
- yuen.decided: decided 2026-10-03 by accounting "From April 2027 the closing day moves to the 20th. Decided for this material"
- yuen.sha256: 86e2461203be3e7c
- yuen.status: ok
- yuen from -> payment_policy v1
- yuen satisfied by -> file "src/pay.py"
- yuen verified by -> file "tests/test_pay.py"
- yuen replaces -> month_end_close v1

# Specification: payment_policy
- yuen.file: policy.req
- yuen.version: 1
- yuen.description: A test material: the policy the requirements of the payment day come from, read and decided from the clause of an example set of terms. Written as an example; not real payment terms

## payment_policy v1: payment_policy (yuen requirement)
The price of an invoice received is paid within 60 days of the closing day
- yuen.owner: accounting
- yuen.decided: decided 2026-09-01 by accounting "Clause 4's 'from the closing day' is read as counted from the day after the closing day. Decided for this material"
- yuen.sha256: 0a46828266bf9f74
- yuen.status: ok
- yuen from -> terms
- yuen satisfied by -> file "src/pay.py"
- yuen verified by -> file "tests/test_pay.py"

# Specification: sources

## terms (yuen source)
- yuen.file: docs/terms.md
- yuen.url: https://example.org/terms.md
- yuen.sha256: 9b646f638f835af8

# Specification: artifacts

## file "src/close.py" (yuen artifact)
- yuen.sha256: 9bb0abb20fa56cb7
- yuen.end: file

## file "src/pay.py" (yuen artifact)
- yuen.sha256: 93e39b25842afd07
- yuen.end: file

## file "tests/test_pay.py" (yuen artifact)
- yuen.sha256: df4a7416b584ec48
- yuen.end: file
