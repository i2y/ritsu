# extension_fees

# Specification: extension_fees
- yuen.file: extension_fees.req
- yuen.version: 1
- yuen.description: Where the tables of the rule extension_fees.rule come from: two sections of 37 CFR part 1, copied here and pinned (the copies have the bytes of the rule's own), and the rule's tables named one by one. A test material; the rule is a sketch and does not say how any regulation is read

## standard_fee v1: standard_fee (yuen requirement)
The fee for an extension of time to reply is set by the month of the reply, from the first to the fifth, and no fee is charged when no extension is taken
- yuen.inForce: 2026-01-01..
- yuen.owner: legal
- yuen.waived: not verified "That the table covers every month and that its rows do not overlap is checked by rulec. This material has no claim that names it"
  approved 2026-10-04 by legal sha256:717b0eb89e528849
- yuen.sha256: 717b0eb89e528849
- yuen.status: ok
- yuen from -> cfr §1.17
- yuen satisfied by -> rulec "rules/extension_fees.rule" table standard_fee
- yuen satisfied by -> rulec "rules/extension_fees.rule" clause no_extension

## small_entity_fee v1: small_entity_fee (yuen requirement)
A small entity pays the lower fee of its own table for a reply made by the date the table holds to
- yuen.inForce: 2026-01-01..
- yuen.owner: legal
- yuen.waived: not verified "That the small entity's table is read before the standard table is checked by rulec. This material has no claim that names it"
  approved 2026-10-04 by legal sha256:a1a6e62ebeedb230
- yuen.sha256: a1a6e62ebeedb230
- yuen.status: ok
- yuen from -> cfr §1.27
- yuen satisfied by -> rulec "rules/extension_fees.rule" table small_entity_fee
- yuen satisfied by -> rulec "rules/extension_fees.rule" define reduced_period

# Specification: sources

## cfr §1.17 (yuen source)
§ 1.17 Patent application and reexamination processing fees.
Link to an amendment published at 89 FR 92004, Nov. 20, 2024.
Link to a correction of the above amendment published at 90 FR 3037, Jan. 14, 2025.
Link to a correction published at 90 FR 3037, Jan. 14, 2025.
(a) Extension fees pursuant to § 1.136(a), except in provisional applications filed under § 1.53(c):
(1) For reply within first month:
Table 1 to Paragraph (a)(1)
By a micro entity (§ 1.29)
$47.00
By a small entity (§ 1.27(a))
94.00
By other than a small or micro entity
235.00
(2) For reply within second month:
Table 2 to Paragraph (a)(2)
By a micro entity (§ 1.29)
$138.00
By a small entity (§ 1.27(a))
276.00
By other than a small or micro entity
690.00
(3) For reply within third month:
Table 3 to Paragraph (a)(3)
By a micro entity (§ 1.29)
$318.00
By a small entity (§ 1.27(a))
636.00
By other than a small or micro entity
1,590.00
(4) For reply within fourth month:
Table 4 to Paragraph (a)(4)
By a micro entity (§ 1.29)
$499.00
By a small entity (§ 1.27(a))
998.00
By other than a small or micro entity
2,495.00
(5) For reply within fifth month:
Table 5 to Paragraph (a)(5)
By a micro entity (§ 1.29)
$679.00
By a small entity (§ 1.27(a))
1,358.00
By other than a small or micro entity
3,395.00
(b) For fees in proceedings before the Patent Trial and Appeal Board, see § 41.20 and § 42.15 of this title.
(c) For filing a request for prioritized examination under § 1.102(e):
Table 6 to Paragraph (c)
By a micro entity (§ 1.29)
$903.00
By a small entity (§ 1.27(a))
1,806.00
By other than a small or micro entity
4,515.00
(d) For correction of inventorship in an application after the first action on the merits:
Table 7 to Paragraph (d)
By a micro entity (§ 1.29)
$138.00
By a small entity (§ 1.27(a))
276.00
By other than a small or micro entity
690.00
(e) To request continued examination pursuant to § 1.114:
(1) For filing a first request for continued examination pursuant to § 1.114 in an application:
Table 8 to Paragraph (e)(1)
By a micro entity (§ 1.29)
$300.00
By a small entity (§ 1.27(a))
600.00
By other than a small or micro entity
1,500.00
(2) For filing a second or subsequent request for continued examination pursuant to § 1.114 in an application:
Table 9 to Paragraph (e)(2)
By a micro entity (§ 1.29)
$572.00
By a small entity (§ 1.27(a))
1,144.00
By other than a small or micro entity
2,860.00
(f) For filing a petition under one of the following sections that refers to this paragraph (f):
Table 10 to Paragraph (f)
By a micro entity (§ 1.29)
$90.00
By a small entity (§ 1.27(a))
180.00
By other than a small or micro entity
450.00
Note 1 to table 10 to paragraph (f):
§ 1.36(a)—for revocation of a power of attorney by fewer than all of the applicants.
§ 1.53(e)—to accord a filing date.
§ 1.182—for decision on a question not specifically provided for in an application for patent.
§ 1.183—to suspend the rules in an application for patent.
§ 1.741(b)—to accord a filing date to an application under § 1.740 for extension of a patent term.
§ 1.1023—to review the filing date of an international design application.
(g)(1) For filing a petition under one of the following sections which refers to this paragraph (g):
Table 11 to Paragraph (g)
By a micro entity (§ 1.29)
$47.00
By a small entity (§ 1.27(a))
94.00
By other than a small or micro entity
235.00
Note 2 to table 11 to paragraph (g)(1):
§ 1.12—for access to an assignment record.
§ 1.14—for access to an application.
§ 1.46—for filing an application on behalf of an inventor by a person who otherwise shows sufficient proprietary interest in the matter.
§ 1.55(f)—for filing a belated certified copy of a foreign application.
§ 1.55(g)—for filing a belated certified copy of a foreign application.
§ 1.57(a)—for filing a belated certified copy of a foreign application.
§ 1.59—for expungement of information.
§ 1.136(b)—for review of a request for extension of time when the provisions of § 1.136(a) are not available.
§ 1.377—for review of decision refusing to accept and record payment of a maintenance fee filed prior to expiration of a patent.
§ 1.550(c)—for patent owner requests for extension of time in ex parte reexamination proceedings.
§ 1.956—for patent owner requests for extension of time in inter partes reexamination proceedings.
§ 5.12 of this chapter—for expedited handling of a foreign filing license.
§ 5.15 of this chapter—for changing the scope of a license.
§ 5.25 of this chapter—for retroactive license.
(2) For filing a petition to suspend action in an application under § 1.103(a):
(i) For filing a first request for suspension pursuant to § 1.103(a) in an application:
Table 12 to Paragraph (g)(2)(i)
By a micro entity (§ 1.29)
$60.00
By a small entity (§ 1.27(a))
120.00
By other than a small or micro entity
300.00
(ii) For filing a second or subsequent request for suspension pursuant to § 1.103(a) in an application:
Table 13 to Paragraph (g)(2)(ii)
By a micro entity (§ 1.29)
$90.00
By a small entity (§ 1.27(a))
180.00
By other than a small or micro entity
450.00
(h) For filing a petition under one of the following sections that refers to this paragraph (h):
Table 12 to Paragraph (h)
By a micro entity (§ 1.29)
$30.00
By a small entity (§ 1.27(a))
60.00
By other than a small or micro entity
150.00
Note 3 to table 14 to paragraph (h):
1.84—for accepting color drawings or photographs.
§ 1.91—for entry of a model or exhibit.
§ 1.102(d)—to make an application special.
§ 1.138(c)—to expressly abandon an application to avoid publication.
§ 1.313—to withdraw an application from issue.
§ 1.314—to defer issuance of a patent.
(i) Processing fees. (1) For taking action under one of the following sections that refers to this paragraph (i)(1):
Table 13 to Paragraph (i)(1)
By a micro entity (§ 1.29)
$30.00
By a small entity (§ 1.27(a))
60.00
By other than a small or micro entity
150.00
Note 4 to table 15 to paragraph (i)(1):
§ 1.28(c)(3)—for processing a non-itemized fee deficiency based on an error in small entity status.
§ 1.29(k)(3)—for processing a non-itemized fee deficiency based on an error in micro entity status.
§ 1.41(b)—for supplying the name or names of the inventor or joint inventors in an application without either an application data sheet or the inventor's oath or declaration, except in provisional applications.
§ 1.48—for correcting inventorship, except in provisional applications.
§ 1.52(d)—for processing a nonprovisional application filed with a specification in a language other than English.
§ 1.53(c)(3)—to convert a provisional application filed under § 1.53(c) into a nonprovisional application under § 1.53(b).
§ 1.71(g)(2)—for processing a belated amendment under § 1.71(g).
§ 1.102(e)—for requesting prioritized examination of an application.
§ 1.103(b)—for requesting limited suspension of action, continued prosecution application for a design patent (§ 1.53(d)).
§ 1.103(c)—for requesting limited suspension of action, request for continued examination (§ 1.114).
§ 1.103(d)—for requesting deferred examination of an application.
§ 1.291(c)(5)—for processing a second or subsequent protest by the same real party in interest.
§ 3.81 of this chapter—for a patent to issue to assignee, assignment submitted after payment of the issue fee.
(2) For taking action under one of the following sections that refers to this paragraph (i)(2):
Table 14 to Paragraph (i)(2)
By a micro entity (§ 1.29)
$151.00
By a small entity (§ 1.27(a))
151.00
By other than a small or micro entity
151.00
Note 5 to table 16 to paragraph (i)(2):
§ 1.217—for processing a redacted copy of a paper submitted in the file of an application in which a redacted copy was submitted for the patent application publication.
§ 1.221—for requesting voluntary publication or republication of an application.
(j) [Reserved]-
(l) [Reserved]
(m)(1) For filing a petition under one of the following sections which refers to this paragraph (m), when the petition is filed more than two years after the date when the required action was due:
Table 18 to Paragraph (m)(1)
By a micro entity (§ 1.29)
$600.00
By a small entity (§ 1.27(a))
1,200.00
By other than a small or micro entity
3,000.00
Note 6 to table 18 to paragraph (m)(1):
§ 1.55(e)—for the delayed submission of a priority claim, when the petition is filed more than two years after the date when the priority claim was due.
§ 1.78(c) or (e)—for the delayed submission of a benefit claim, when the petition is filed more than two years after the date when the benefit claim was due.
§ 1.137—for filing a petition for the revival of an abandoned application for a patent, or for the delayed payment of the fee for issuing each patent, when the petition is filed more than two years after the abandonment of the application.
§ 1.137—for filing a petition for the revival of a reexamination proceeding that was terminated or limited due to a delayed response by the patent owner, when the petition is filed more than two years after the termination or limitation of the reexamination proceeding.
§ 1.378—for filing a petition to accept a delayed payment of the fee for maintaining a patent in force, when the petition is filed more than two years after the patent expiration date.
§ 1.1051—for filing a petition to excuse an applicant's failure to act within prescribed time limits in an international design application, when the petition is filed more than two years after the abandonment of the application.
(2) For filing a petition under § 1.55(e), § 1.78(c), § 1.78(e), § 1.137, § 1.1051, or § 1.378, when the petition is filed before the time period specified in paragraph (m)(1) of this section:
Table 19 to Paragraph (m)(2)
By a micro entity (§ 1.29)
$452.00
By a small entity (§ 1.27(a))
904.00
By other than a small or micro entity
2,260.00
(3) For filing a petition under § 1.55(c), § 1.78(b), or § 1.452 for the extension of the 12-month (six-month for designs) period for filing a subsequent application:
Table 20 to Paragraph (m)(3)
By a micro entity (§ 1.29)
$452.00
By a small entity (§ 1.27(a))
904.00
By other than a small or micro entity
2,260.00
(n) [Reserved]
(o) For every ten items or fraction thereof in a third-party submission under § 1.290:
Table 17 to Paragraph (o)
By a small entity (§ 1.27(a)) or micro entity (§ 1.29)
$78.00
By other than a small or micro entity
195.00
(p) For an information disclosure statement under § 1.97(c) or (d):
Table 18 to Paragraph (p)
By a micro entity (§ 1.29)
$56.00
By a small entity (§ 1.27(a))
112.00
By other than a small or micro entity
280.00
(q) Processing fee for taking action under one of the following sections which refers to this paragraph (q): $54.00.
(1) Section 1.41—to supply the name or names of the inventor or inventors after the filing date without a cover sheet as prescribed by § 1.51(c)(1) in a provisional application.
(2) Section 1.48—for correction of inventorship in a provisional application.
(3) Section 1.53(c)(2)—to convert a nonprovisional application filed under § 1.53(b) to a provisional application under § 1.53(c).
(r) For entry of a submission after final rejection under § 1.129(a):
Table 19 to Paragraph (r)
By a micro entity (§ 1.29)
$189.00
By a small entity (§ 1.27(a))
378.00
By other than a small or micro entity
945.00
(s) For each additional invention requested to be examined under § 1.129(b):
Table 20 to Paragraph (s)
By a micro entity (§ 1.29)
$189.00
By a small entity (§ 1.27(a))
378.00
By other than a small or micro entity
945.00
(t) For filing a petition to convert an international design application to a design application under 35 U.S.C. chapter 16 (§ 1.1052):
Table 21 to Paragraph (t)
By a micro entity (§ 1.29)
$39.00
By a small entity (§ 1.27(a))
78.00
By other than a small or micro entity
195.00
(u) Extension fees pursuant to § 1.136(a) in provisional applications filed under § 1.53(c):
(1) For reply within first month:
Table 26 to Paragraph (u)(1)
By a micro entity (§ 1.29)
$10.00
By a small entity (§ 1.27(a))
20.00
By other than a small or micro entity
50.00
(2) For reply within second month:
Table 27 to Paragraph (u)(2)
By a micro entity (§ 1.29)
$20.00
By a small entity (§ 1.27(a))
40.00
By other than a small or micro entity
100.00
(3) For reply within third month:
Table 28 to Paragraph (u)(3)
By a micro entity (§ 1.29)
$40.00
By a small entity (§ 1.27(a))
80.00
By other than a small or micro entity
200.00
(4) For reply within fourth month:
Table 29 to Paragraph (u)(4)
By a micro entity (§ 1.29)
$80.00
By a small entity (§ 1.27(a))
160.00
By other than a small or micro entity
400.00
(5) For reply within fifth month:
Table 30 to Paragraph (u)(5)
By a micro entity (§ 1.29)
$160.00
By a small entity (§ 1.27(a))
320.00
By other than a small or micro entity
800.00
(v) Information disclosure statement size fee for an information disclosure statement filed under § 1.97 that, inclusive of the number of applicant-provided or patent owner-provided items of information listed under § 1.98(a)(1) on the information disclosure statement, causes the cumulative number of applicant-provided or patent owner-provided items of information under § 1.98(a)(1) during the pendency of the application or reexamination proceeding to:
(1) Exceed 50 but not exceed 100. . . . . .$200;
(2) Exceed 100 but not exceed 200. . . . . .$500, less any amount previously paid under paragraph (v)(1) of this section; and
(3) Exceed 200. . . . . .$800, less any amounts previously paid under paragraphs (v)(1) and/or (2) of this section.
(w) Additional fee for presenting a benefit claim in a nonprovisional application under 35 U.S.C. 120, 121, 365(c), or 386(c) and § 1.78(d):
(1) When the actual filing date of the nonprovisional application in which the benefit claim is presented is more than six years and no more than nine years from the earliest filing date for which benefit is claimed under 35 U.S.C. 120, 121, 365(c), or 386(c) and § 1.78(d):
Table 31 to Paragraph (w)(1)
By a micro entity (§ 1.29)
$540.00
By a small entity (§ 1.27(a))
1,080.00
By other than a small or micro entity
2,700.00
(2) When the actual filing date of the nonprovisional application in which the benefit claim is presented is more than nine years from the earliest filing date for which benefit is claimed under 35 U.S.C. 120, 121, 365(c), or 386(c) and § 1.78(d), the amount shown in this paragraph is due, less any amount previously paid under paragraph (w)(1) of this section:
Table 32 to Paragraph (w)(2)
By a micro entity (§ 1.29)
$800.00
By a small entity (§ 1.27(a))
1,600.00
By other than a small or micro entity
4,000.00
[78 FR 17105, Mar. 20, 2013, as amended at 78 FR 62395, Oct. 21, 2013; 78 FR 75252, Dec. 11, 2013; 80 FR 17954, Apr. 2, 2015; 82 FR 52814, Nov. 14, 2017; 85 FR 46986, Aug. 3, 2020; 85 FR 58283, Sept. 18, 2020; 88 FR 17154, Mar. 22, 2023; 89 FR 92004, Nov. 20, 2024; 90 FR 39126, Aug. 14, 2025]
- yuen.law: ecfr 37 CFR 1
- yuen.asof: 2026-01-01
- yuen.sha256: 9b48f2c46284140a

## cfr §1.27 (yuen source)
§ 1.27 Definition of small entities and establishing status as a small entity to permit payment of small entity fees; when a determination of entitlement to small entity status and notification of loss of entitlement to small entity status are required; fraud on the Office.
(a) Definition of small entities. A small entity as used in this chapter means any party (person, small business concern, or nonprofit organization) under paragraphs (a)(1) through (a)(3) of this section.
(1) Person. A person, as used in paragraph (c) of this section, means any inventor or other individual (e.g., an individual to whom an inventor has transferred some rights in the invention) who has not assigned, granted, conveyed, or licensed, and is under no obligation under contract or law to assign, grant, convey, or license, any rights in the invention. An inventor or other individual who has transferred some rights in the invention to one or more parties, or is under an obligation to transfer some rights in the invention to one or more parties, can also qualify for small entity status if all the parties who have had rights in the invention transferred to them also qualify for small entity status either as a person, small business concern, or nonprofit organization under this section.
(2) Small business concern. A small business concern, as used in paragraph (c) of this section, means any business concern that:
(i) Has not assigned, granted, conveyed, or licensed, and is under no obligation under contract or law to assign, grant, convey, or license, any rights in the invention to any person, concern, or organization which would not qualify for small entity status as a person, small business concern, or nonprofit organization; and
(ii) Meets the size standards set forth in 13 CFR 121.801 through 121.805 to be eligible for reduced patent fees. Questions related to standards for a small business concern may be directed to: Small Business Administration, Size Standards Staff, 409 Third Street, SW., Washington, DC 20416.
(3) Nonprofit organization. A nonprofit organization, as used in paragraph (c) of this section, means any nonprofit organization that:
(i) Has not assigned, granted, conveyed, or licensed, and is under no obligation under contract or law to assign, grant, convey, or license, any rights in the invention to any person, concern, or organization which would not qualify as a person, small business concern, or a nonprofit organization; and
(ii) Is either:
(A) A university or other institution of higher education located in any country;
(B) An organization of the type described in section 501(c)(3) of the Internal Revenue Code of 1986 (26 U.S.C. 501(c)(3)) and exempt from taxation under section 501(a) of the Internal Revenue Code (26 U.S.C. 501(a));
(C) Any nonprofit scientific or educational organization qualified under a nonprofit organization statute of a state of this country (35 U.S.C. 201(i)); or
(D) Any nonprofit organization located in a foreign country which would qualify as a nonprofit organization under paragraphs (a)(3)(ii)(B) of this section or (a)(3)(ii)(C) of this section if it were located in this country.
(4) Federal Government Use License Exceptions. In a patent application filed, prosecuted, and if patented, maintained at no expense to the Government, with the exception of any expense taken to deliver the application and fees to the Office on behalf of the applicant:
(i) For persons under paragraph (a)(1) of this section, claiming small entity status is not prohibited by:
(A) A use license to the Government resulting from a rights determination under Executive Order 10096 made in accordance with § 501.6 of this title;
(B) A use license to the Government resulting from Federal agency action pursuant to 15 U.S.C. 3710d(a) allowing the Federal employee-inventor to obtain or retain title to the invention; or
(C) A use license to a Federal agency resulting from retention of rights under 35 U.S.C. 202(d) by an inventor employed by a small business concern or nonprofit organization contractor, provided the license is equivalent to the license under 35 U.S.C. 202(c)(4) the Federal agency would have received had the contractor elected to retain title, and all the conditions applicable under § 401.9 of this title to an employee/inventor are met.
(ii) For small business concerns and nonprofit organizations under paragraphs (a)(2) and (3) of this section, a use license to a Federal agency resulting from a funding agreement with that agency pursuant to 35 U.S.C. 202(c)(4) does not preclude claiming small entity status, provided that:
(A) The subject invention was made solely by employees of the small business concern or nonprofit organization; or
(B) In the case of a Federal employee co-inventor, the Federal agency employing such co-inventor took action pursuant to 35 U.S.C. 202(e)(1) to exclusively license or assign whatever rights currently held or that it may acquire in the subject invention to the small business concern or nonprofit organization, subject to the license under 35 U.S.C. 202(c)(4).
(iii) For small business concerns and nonprofit organizations under paragraphs (a)(2) and (3) of this section that have collaborated with a Federal agency laboratory pursuant to a cooperative research and development agreement (CRADA) under 15 U.S.C. 3710a(a)(1), claiming small entity status is not prohibited by a use license to the Government pursuant to:
(A) 15 U.S.C. 3710a(b)(2) that results from retaining title to an invention made solely by the employee of the small business concern or nonprofit organization; or
(B) 15 U.S.C. 3710a(b)(3)(D), provided the laboratory has waived in whole any right of ownership the Government may have to the subject invention made by the small business concern or nonprofit organization, or has exclusively licensed whatever ownership rights the Government may acquire in the subject invention to the small business concern or nonprofit organization.
(iv) Regardless of whether an exception under this paragraph (a)(4) applies, no refund under § 1.28(a) is available for any patent fee paid by the Government.
(5) Security Interest. A security interest does not involve an obligation to transfer rights in the invention for the purposes of paragraphs (a)(1) through (a)(3) of this section unless the security interest is defaulted upon.
(b) Establishment of small entity status permits payment of reduced fees. (1) A small entity, as defined in paragraph (a) of this section, who has properly asserted entitlement to small entity status pursuant to paragraph (c) of this section will be accorded small entity status by the Office in the particular application or patent in which entitlement to small entity status was asserted. Establishment of small entity status allows the payment of certain reduced patent fees pursuant to 35 U.S.C. 41(h)(1).
(2) Submission of an original utility application in compliance with the USPTO patent electronic filing system by an applicant who has properly asserted entitlement to small entity status pursuant to paragraph (c) of this section in that application allows the payment of a reduced filing fee pursuant to 35 U.S.C. 41(h)(3).
(c) Assertion of small entity status. Any party (person, small business concern or nonprofit organization) should make a determination, pursuant to paragraph (f) of this section, of entitlement to be accorded small entity status based on the definitions set forth in paragraph (a) of this section, and must, in order to establish small entity status for the purpose of paying small entity fees, actually make an assertion of entitlement to small entity status, in the manner set forth in paragraphs (c)(1) or (c)(3) of this section, in the application or patent in which such small entity fees are to be paid.
(1) Assertion by writing. Small entity status may be established by a written assertion of entitlement to small entity status. A written assertion must:
(i) Be clearly identifiable;
(ii) Be signed (see paragraph (c)(2) of this section); and
(iii) Convey the concept of entitlement to small entity status, such as by stating that applicant is a small entity, or that small entity status is entitled to be asserted for the application or patent. While no specific words or wording are required to assert small entity status, the intent to assert small entity status must be clearly indicated in order to comply with the assertion requirement.
(2) Parties who can sign the written assertion. The written assertion can be signed by:
(i) The applicant (§ 1.42 or § 1.421);
(ii) A patent practitioner of record or a practitioner acting in a representative capacity under § 1.34;
(iii) The inventor or a joint inventor, if the inventor is the applicant; or
(iv) The assignee.
(3) Assertion by payment of the small entity basic filing, basic transmittal, basic national fee, international search fee, or individual designation fee in an international design application. The payment, by any party, of the exact amount of one of the small entity basic filing fees set forth in § 1.16(a), (b), (c), (d), or (e), the small entity transmittal fee set forth in § 1.445(a)(1) or § 1.1031(a), the small entity international search fee set forth in § 1.445(a)(2) to a Receiving Office other than the United States Receiving Office in the exact amount established for that Receiving Office pursuant to PCT Rule 16, or the small entity basic national fee set forth in § 1.492(a), will be treated as a written assertion of entitlement to small entity status even if the type of basic filing, basic transmittal, or basic national fee is inadvertently selected in error. The payment, by any party, of the small entity first part of the individual designation fee for the United States to the International Bureau (§ 1.1031) will be treated as a written assertion of entitlement to small entity status.
(i) If the Office accords small entity status based on payment of a small entity basic filing or basic national fee under paragraph (c)(3) of this section that is not applicable to that application, any balance of the small entity fee that is applicable to that application will be due along with the appropriate surcharge set forth in § 1.16(f), or § 1.16(g).
(ii) The payment of any small entity fee other than those set forth in paragraph (c)(3) of this section (whether in the exact fee amount or not) will not be treated as a written assertion of entitlement to small entity status and will not be sufficient to establish small entity status in an application or a patent.
(4) Assertion required in related, continuing, and reissue applications. Status as a small entity must be specifically established by an assertion in each related, continuing and reissue application in which status is appropriate and desired. Status as a small entity in one application or patent does not affect the status of any other application or patent, regardless of the relationship of the applications or patents. The refiling of an application under § 1.53 as a continuation, divisional, or continuation-in-part application (including a continued prosecution application under § 1.53(d)), or the filing of a reissue application, requires a new assertion as to continued entitlement to small entity status for the continuing or reissue application.
(d) When small entity fees can be paid. Any fee, other than the small entity basic filing fees and the small entity national fees of paragraph (c)(3) of this section, can be paid in the small entity amount only if it is submitted with, or subsequent to, the submission of a written assertion of entitlement to small entity status, except when refunds are permitted by § 1.28(a).
(e) Only one assertion required. (1) An assertion of small entity status need only be filed once in an application or patent. Small entity status, once established, remains in effect until changed pursuant to paragraph (g)(1) of this section. Where an assignment of rights or an obligation to assign rights to other parties who are small entities occurs subsequent to an assertion of small entity status, a second assertion is not required.
(2) Once small entity status is withdrawn pursuant to paragraph (g)(2) of this section, a new written assertion is required to again obtain small entity status.
(f) Assertion requires a determination of entitlement to pay small entity fees. Prior to submitting an assertion of entitlement to small entity status in an application, including a related, continuing, or reissue application, a determination of such entitlement should be made pursuant to the requirements of paragraph (a) of this section. It should be determined that all parties holding rights in the invention qualify for small entity status. The Office will generally not question any assertion of small entity status that is made in accordance with the requirements of this section, but note paragraph (h) of this section.
(g)(1) New determination of entitlement to small entity status is needed when issue and maintenance fees are due. Once status as a small entity has been established in an application or patent, fees as a small entity may thereafter be paid in that application or patent without regard to a change in status until the issue fee is due or any maintenance fee is due.
(2) Notification of loss of entitlement to small entity status is required when issue and maintenance fees are due. Notification of a loss of entitlement to small entity status must be filed in the application or patent prior to paying, or at the time of paying, the earliest of the issue fee or any maintenance fee due after the date on which status as a small entity as defined in paragraph (a) of this section is no longer appropriate. The notification that small entity status is no longer appropriate must be signed by a party identified in § 1.33(b). Payment of a fee in other than the small entity amount is not sufficient notification that small entity status is no longer appropriate.
(h) Fraud attempted or practiced on the Office. (1) Any attempt to fraudulently establish status as a small entity, or pay fees as a small entity, shall be considered as a fraud practiced or attempted on the Office.
(2) Improperly, and with intent to deceive, establishing status as a small entity, or paying fees as a small entity, shall be considered as a fraud practiced or attempted on the Office.
[65 FR 54659, Sept. 8, 2000, as amended at 69 FR 56538, Sept. 21, 2004; 70 FR 3889, Jan. 27, 2005; 77 FR 48813, Aug. 14, 2012; 78 FR 4289, Jan. 18, 2013; 80 FR 17955, Apr. 2, 2015; 85 FR 46990, Aug. 3, 2020; 85 FR 82923, Dec. 21, 2020]
- yuen.law: ecfr 37 CFR 1
- yuen.asof: 2026-01-01
- yuen.sha256: fea1289ebe564f77

# Specification: artifacts

## rulec "rules/extension_fees.rule" table standard_fee (yuen artifact)
- yuen.sha256: 9c75e7072bde2938
- yuen.end: item

## rulec "rules/extension_fees.rule" clause no_extension (yuen artifact)
- yuen.sha256: 2391acd18f47abcb
- yuen.end: item

## rulec "rules/extension_fees.rule" table small_entity_fee (yuen artifact)
- yuen.sha256: 5fd98a7705c641eb
- yuen.end: item

## rulec "rules/extension_fees.rule" define reduced_period (yuen artifact)
- yuen.sha256: 611179d6b0c376c4
- yuen.end: item
