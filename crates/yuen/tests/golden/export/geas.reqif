# greeter

# Specification: greeter
- yuen.file: greeter.req
- yuen.version: 1
- yuen.description: What geas's example greeter answers, for the tests: met by its server, checked by the claims of its spec, and read from a contract written for the tests

## greets_by_name v1: greets_by_name (yuen requirement)
GET /greet?name=<name> answers 200 with the message Hello, <name>
- yuen.owner: api
- yuen.sha256: 4e3719f3a07dc096
- yuen.status: ok
- yuen from -> contract
- yuen satisfied by -> file "greeter/server.py"
- yuen verified by -> geas "greeter/greeter.geas" claim "greets by name"

## rejects_an_empty_name v1: rejects_an_empty_name (yuen requirement)
GET /greet with an empty name answers 400
- yuen.owner: api
- yuen.decided: decided 2026-10-03 by api "an empty name is a client error, not a greeting"
- yuen.sha256: 70ec5112e96e51a9
- yuen.status: ok
- yuen from -> contract
- yuen satisfied by -> file "greeter/server.py"
- yuen verified by -> geas "greeter/greeter.geas" claim "rejects an empty name"

## totals_accumulate v1: totals_accumulate (yuen requirement)
POST /add adds its body to a total that GET /total answers, and POST /reset sets it to 0
- yuen.owner: api
- yuen.sha256: 6b134f42eed9f18a
- yuen.status: ok
- yuen from -> contract
- yuen satisfied by -> file "greeter/server.py"
- yuen verified by -> geas "greeter/greeter.geas" claim "totals accumulate across requests"

## unknown_paths_are_404 v1: unknown_paths_are_404 (yuen requirement)
Any other path answers 404
- yuen.owner: api
- yuen.sha256: 132fa5fd5426ca87
- yuen.status: ok
- yuen from -> contract
- yuen satisfied by -> file "greeter/server.py"
- yuen verified by -> geas "greeter/greeter.geas" claim "unknown paths are 404"

# Specification: sources

## contract (yuen source)
- yuen.file: contract.md
- yuen.sha256: 129685aad10b7b82

# Specification: artifacts

## file "greeter/server.py" (yuen artifact)
- yuen.sha256: 331e02e26d128e8c
- yuen.end: file

## geas "greeter/greeter.geas" claim "greets by name" (yuen artifact)
- yuen.sha256: 2b4e11c2cc191431
- yuen.end: item

## geas "greeter/greeter.geas" claim "rejects an empty name" (yuen artifact)
- yuen.sha256: 3f7c8d1b2bbcc309
- yuen.end: item

## geas "greeter/greeter.geas" claim "totals accumulate across requests" (yuen artifact)
- yuen.sha256: d653be1c06f5c8b1
- yuen.end: item

## geas "greeter/greeter.geas" claim "unknown paths are 404" (yuen artifact)
- yuen.sha256: 1950201e8644bc57
- yuen.end: item
