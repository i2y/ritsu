# payment_terms, period_of_months

# Specification: payment_terms
- yuen.file: payment_terms.req
- yuen.version: 1
- yuen.description: A test material: the payment day of koyomi's example payment_20th_close_next_10th.cal. The source of the closed days is borrowed from the table of national holidays the calendar file pins. The terms of payment are written for this material

## payment_day v1: payment_day (yuen requirement)
Closes on the 20th, pays on the 10th of the next month. When the payment day is closed, pays on the business day before
- yuen.inForce: 2026-10-01..
- yuen.owner: accounting
- yuen.sha256: dd7089d2bc2f76e0
- yuen.status: ok
- yuen from -> holidays
- yuen satisfied by -> koyomi "payment_20th_close_next_10th.cal" date payment
- yuen verified by -> koyomi "payment_20th_close_next_10th.cal" claim paid_on_a_business_day

# Specification: period_of_months
- yuen.file: period_of_months.req
- yuen.version: 1
- yuen.description: A test material: the dates and claims of koyomi's example period_of_months.cal, named one by one. The source of the closed days is borrowed from the bank holidays the calendar file pins. Written for this material; it does not say how any rule is read

## first_day v1: first_day (yuen requirement)
The day itself is not counted
- yuen.inForce: 2026-10-01..
- yuen.owner: legal
- yuen.decided: decided 2026-10-03 by legal "The period starts on the day after the origin. Decided for this material"
- yuen.waived: not verified "That the first day is not counted is checked on koyomi doc's page, by reading the rule and its restatement side by side. This material has no claim that checks it"
  approved 2026-10-04 by legal sha256:29836b1424129486
- yuen.sha256: 29836b1424129486
- yuen.status: ok
- yuen satisfied by -> koyomi "period_of_months.cal" date first_day

## last_day v1: last_day (yuen requirement)
A period of months ends on the day before the corresponding day of the last month, or on the last day of that month when it has no such day
- yuen.inForce: 2026-10-01..
- yuen.owner: legal
- yuen.decided: decided 2026-10-03 by legal "The corresponding day is counted from the first day. Decided for this material"
- yuen.sha256: 534cb97e1ca8a94c
- yuen.status: ok
- yuen satisfied by -> koyomi "period_of_months.cal" date last_day
- yuen verified by -> koyomi "period_of_months.cal" claim last_day_after_origin

## last_day_moved v1: last_day_moved (yuen requirement)
An end that falls on a day closed in England and Wales moves to the day after
- yuen.inForce: 2026-10-01..
- yuen.owner: legal
- yuen.decided: decided 2026-10-03 by legal "The day after is taken as it is, and not moved on if it is closed too. Decided for this material"
- yuen.sha256: edc4cc0bb4910f57
- yuen.status: ok
- yuen from -> bank_holidays
- yuen satisfied by -> koyomi "period_of_months.cal" date last_day_moved
- yuen verified by -> koyomi "period_of_months.cal" claim moved_on_or_after_last_day

# Specification: sources

## holidays (yuen source)
- yuen.file: calendars/data/syukujitsu.csv
- yuen.url: https://www8.cao.go.jp/chosei/shukujitsu/syukujitsu.csv
- yuen.sha256: cec37a743c96995c

## bank_holidays (yuen source)
- yuen.file: calendars/data/bank-holidays.json
- yuen.url: https://www.gov.uk/bank-holidays.json
- yuen.sha256: 538b3482c28b85ec

# Specification: artifacts

## koyomi "payment_20th_close_next_10th.cal" date payment (yuen artifact)
- yuen.sha256: 77727589d8318079
- yuen.end: item

## koyomi "payment_20th_close_next_10th.cal" claim paid_on_a_business_day (yuen artifact)
- yuen.sha256: a30c094c89e283df
- yuen.end: item

## koyomi "period_of_months.cal" date first_day (yuen artifact)
- yuen.sha256: f7fbde9442fad208
- yuen.end: item

## koyomi "period_of_months.cal" date last_day (yuen artifact)
- yuen.sha256: e4d5741e15aeb403
- yuen.end: item

## koyomi "period_of_months.cal" claim last_day_after_origin (yuen artifact)
- yuen.sha256: d88a046cef583e8a
- yuen.end: item

## koyomi "period_of_months.cal" date last_day_moved (yuen artifact)
- yuen.sha256: da1536d15d1da2b6
- yuen.end: item

## koyomi "period_of_months.cal" claim moved_on_or_after_last_day (yuen artifact)
- yuen.sha256: 82aece4919f854bb
- yuen.end: item
