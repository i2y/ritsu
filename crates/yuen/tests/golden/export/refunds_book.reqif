# refund

# Specification: refund
- yuen.file: refund.req
- yuen.version: 1
- yuen.description: A test material: the accounts and transfers of chobo's example refunds.book, named one by one, and where in the refund policy they come from. The source is a copy of the policy's document, pinned; what meets a requirement is an account or a transfer

## within_sales v1: within_sales (yuen requirement)
A refund does not exceed the sale of its order
- yuen.inForce: 2026-10-01..
- yuen.owner: accounting
- yuen.waived: not verified "That what is left never goes below 0 is checked by chobo's check. This material has no claim that names it"
  approved 2026-10-04 by accounting sha256:03c54d3019572784
- yuen.sha256: 03c54d3019572784
- yuen.status: ok
- yuen from -> policy
- yuen satisfied by -> chobo "refunds.book" account refundable
- yuen satisfied by -> chobo "refunds.book" transfer sale

## hold_until_approved v1: hold_until_approved (yuen requirement)
A refund is not final until a person approves it. While it waits for approval, the amount is held
- yuen.inForce: 2026-10-01..
- yuen.owner: accounting
- yuen.waived: not verified "That the amount held returns at the expiry is checked by chobo's scenarios. This material has no claim that names it"
  approved 2026-10-04 by accounting sha256:beb5b3ab5c01bf55
- yuen.sha256: beb5b3ab5c01bf55
- yuen.status: ok
- yuen from -> policy
- yuen satisfied by -> chobo "refunds.book" transfer refund

## record_together v1: record_together (yuen requirement)
The amount refunded is recorded in total, not per order
- yuen.inForce: 2026-10-01..
- yuen.owner: accounting
- yuen.waived: not verified "This material has no claim that checks it"
  approved 2026-10-04 by accounting sha256:166eee17bb57e3e0
- yuen.sha256: 166eee17bb57e3e0
- yuen.status: ok
- yuen from -> policy
- yuen satisfied by -> chobo "refunds.book" account refunded

# Specification: sources

## policy (yuen source)
- yuen.file: refund_policy.md
- yuen.sha256: 784ec7d47b0919f5

# Specification: artifacts

## chobo "refunds.book" account refundable (yuen artifact)
- yuen.sha256: 49d9b3dd2d4bf83b
- yuen.end: item

## chobo "refunds.book" transfer sale (yuen artifact)
- yuen.sha256: 699a4feaa65a1dfe
- yuen.end: item

## chobo "refunds.book" transfer refund (yuen artifact)
- yuen.sha256: d4eb1e0e94a3b78f
- yuen.end: item

## chobo "refunds.book" account refunded (yuen artifact)
- yuen.sha256: 8f80f74b076ccea8
- yuen.end: item
