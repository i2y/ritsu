# osha

# Specification: osha
- yuen.file: osha.req
- yuen.version: 1
- yuen.description: A requirement read from 29 CFR 1910.157, for the tests. Written as an example; it does not say how the regulation is to be read

## extinguisher_distance v1: extinguisher_distance (yuen requirement)
No employee travels more than 75 feet to a portable fire extinguisher for Class A fires
- yuen.owner: safety
- yuen.waived: not satisfied "The test material names no artifact"
  approved 2026-10-03 by safety sha256:08a4819829372b9b
  not verified "The test material names no claim"
  approved 2026-10-03 by safety sha256:08a4819829372b9b
- yuen.sha256: 08a4819829372b9b
- yuen.status: ok
- yuen from -> osha §1910.157

# Specification: sources

## osha §1910.157 (yuen source)
§ 1910.157 Portable fire extinguishers.
(a) Scope and application. The requirements of this section apply to the placement, use, maintenance, and testing of portable fire extinguishers provided for the use of employees. Paragraph (d) of this section does not apply to extinguishers provided for employee use on the outside of workplace buildings or structures. Where extinguishers are provided but are not intended for employee use and the employer has an emergency action plan and a fire prevention plan that meet the requirements of 29 CFR 1910.38 and 29 CFR 1910.39 respectively, then only the requirements of paragraphs (e) and (f) of this section apply.
(b) Exemptions. (1) Where the employer has established and implemented a written fire safety policy which requires the immediate and total evacuation of employees from the workplace upon the sounding of a fire alarm signal and which includes an emergency action plan and a fire prevention plan which meet the requirements of 29 CFR 1910.38 and 29 CFR 1910.39 respectively, and when extinguishers are not available in the workplace, the employer is exempt from all requirements of this section unless a specific standard in part 1910 requires that a portable fire extinguisher be provided.
(2) Where the employer has an emergency action plan meeting the requirements of § 1910.38 which designates certain employees to be the only employees authorized to use the available portable fire extinguishers, and which requires all other employees in the fire area to immediately evacuate the affected work area upon the sounding of the fire alarm, the employer is exempt from the distribution requirements in paragraph (d) of this section.
(c) General requirements. (1) The employer shall provide portable fire extinguishers and shall mount, locate and identify them so that they are readily accessible to employees without subjecting the employees to possible injury.
(2) Only approved portable fire extinguishers shall be used to meet the requirements of this section.
(3) The employer shall not provide or make available in the workplace portable fire extinguishers using carbon tetrachloride or chlorobromomethane extinguishing agents.
(4) The employer shall assure that portable fire extinguishers are maintained in a fully charged and operable condition and kept in their designated places at all times except during use.
(5) The employer shall remove from service all soldered or riveted shell self-generating soda acid or self-generating foam or gas cartridge water type portable fire extinguishers which are operated by inverting the extinguisher to rupture the cartridge or to initiate an uncontrollable pressure generating chemical reaction to expel the agent.
(d) Selection and distribution. (1) Portable fire extinguishers shall be provided for employee use and selected and distributed based on the classes of anticipated workplace fires and on the size and degree of hazard which would affect their use.
(2) The employer shall distribute portable fire extinguishers for use by employees on Class A fires so that the travel distance for employees to any extinguisher is 75 feet (22.9 m) or less.
(3) The employer may use uniformly spaced standpipe systems or hose stations connected to a sprinkler system installed for emergency use by employees instead of Class A portable fire extinguishers, provided that such systems meet the respective requirements of § 1910.158 or § 1910.159, that they provide total coverage of the area to be protected, and that employees are trained at least annually in their use.
(4) The employer shall distribute portable fire extinguishers for use by employees on Class B fires so that the travel distance from the Class B hazard area to any extinguisher is 50 feet (15.2 m) or less.
(5) The employer shall distribute portable fire extinguishers used for Class C hazards on the basis of the appropriate pattern for the existing Class A or Class B hazards.
(6) The employer shall distribute portable fire extinguishers or other containers of Class D extinguishing agent for use by employees so that the travel distance from the combustible metal working area to any extinguishing agent is 75 feet (22.9 m) or less. Portable fire extinguishers for Class D hazards are required in those combustible metal working areas where combustible metal powders, flakes, shavings, or similarly sized products are generated at least once every two weeks.
(e) Inspection, maintenance and testing. (1) The employer shall be responsible for the inspection, maintenance and testing of all portable fire extinguishers in the workplace.
(2) Portable extinguishers or hose used in lieu thereof under paragraph (d)(3) of this section shall be visually inspected monthly.
(3) The employer shall assure that portable fire extinguishers are subjected to an annual maintenance check. Stored pressure extinguishers do not require an internal examination. The employer shall record the annual maintenance date and retain this record for one year after the last entry or the life of the shell, whichever is less. The record shall be available to the Assistant Secretary upon request.
(4) The employer shall assure that stored pressure dry chemical extinguishers that require a 12-year hydrostatic test are emptied and subjected to applicable maintenance procedures every 6 years. Dry chemical extinguishers having non-refillable disposable containers are exempt from this requirement. When recharging or hydrostatic testing is performed, the 6-year requirement begins from that date.
(5) The employer shall assure that alternate equivalent protection is provided when portable fire extinguishers are removed from service for maintenance and recharging.
(f) Hydrostatic testing. (1) The employer shall assure that hydrostatic testing is performed by trained persons with suitable testing equipment and facilities.
(2) The employer shall assure that portable extinguishers are hydrostatically tested at the intervals listed in Table L-1 of this section, except under any of the following conditions:
(i) When the unit has been repaired by soldering, welding, brazing, or use of patching compounds;
(ii) When the cylinder or shell threads are damaged;
(iii) When there is corrosion that has caused pitting, including corrosion under removable name plate assemblies;
(iv) When the extinguisher has been burned in a fire; or
(v) When a calcium chloride extinguishing agent has been used in a stainless steel shell.
(3) In addition to an external visual examination, the employer shall assure that an internal examination of cylinders and shells to be tested is made prior to the hydrostatic tests.
Table L-1
Type of extinguishers
Test interval (years)
Soda acid (soldered brass shells) (until 1/1/82)
(1)
Soda acid (stainless steel shell)
5
Cartridge operated water and/or antifreeze
5
Stored pressure water and/or antifreeze
5
Wetting agent
5
Foam (soldered brass shells) (until 1/1/82)
(1)
Foam (stainless steel shell)
5
Aqueous Film Forming foam (AFFF)
5
Loaded stream
5
Dry chemical with stainless steel
5
Carbon dioxide
5
Dry chemical, stored pressure, with mild steel, brazed brass or aluminum shells
12
Dry chemical, cartridge or cylinder operated, with mild steel shells
12
Halon 1211
12
Halon 1301
12
Dry powder, cartridge or cylinder operated with mild steel shells
12
1 Extinguishers having shells constructed of copper or brass joined by soft solder or rivets shall not be hydrostatically tested and shall be removed from service by January 1, 1982. (Not permitted)
(4) The employer shall assure that portable fire extinguishers are hydrostatically tested whenever they show new evidence of corrosion or mechanical injury, except under the conditions listed in paragraphs (f)(2)(i)-(v) of this section.
(5) The employer shall assure that hydrostatic tests are performed on extinguisher hose assemblies which are equipped with a shut-off nozzle at the discharge end of the hose. The test interval shall be the same as specified for the extinguisher on which the hose is installed.
(6) The employer shall assure that carbon dioxide hose assemblies with a shut-off nozzle are hydrostatically tested at 1,250 psi (8,620 kPa).
(7) The employer shall assure that dry chemical and dry powder hose assemblies with a shut-off nozzle are hydrostatically tested at 300 psi (2,070 kPa).
(8) Hose assemblies passing a hydrostatic test do not require any type of recording or stamping.
(9) The employer shall assure that hose assemblies for carbon dioxide extinguishers that require a hydrostatic test are tested within a protective cage device.
(10) The employer shall assure that carbon dioxide extinguishers and nitrogen or carbon dioxide cylinders used with wheeled extinguishers are tested every 5 years at 5/3 of the service pressure as stamped into the cylinder. Nitrogen cylinders which comply with 49 CFR 173.34(e)(15) may be hydrostatically tested every 10 years.
(11) The employer shall assure that all stored pressure and Halon 1211 types of extinguishers are hydrostatically tested at the factory test pressure not to exceed two times the service pressure.
(12) The employer shall assure that acceptable self-generating type soda acid and foam extinguishers are tested at 350 psi (2,410 kPa).
(13) Air or gas pressure may not be used for hydrostatic testing.
(14) Extinguisher shells, cylinders, or cartridges which fail a hydrostatic pressure test, or which are not fit for testing shall be removed from service and from the workplace.
(15)(i) The equipment for testing compressed gas type cylinders shall be of the water jacket type. The equipment shall be provided with an expansion indicator which operates with an accuracy within one percent of the total expansion or .1cc (.1mL) of liquid.
(ii) The equipment for testing non-compressed gas type cylinders shall consist of the following:
(A) A hydrostatic test pump, hand or power operated, capable of producing not less than 150 percent of the test pressure, which shall include appropriate check valves and fittings;
(B) A flexible connection for attachment to fittings to test through the extinguisher nozzle, test bonnet, or hose outlet, as is applicable; and
(C) A protective cage or barrier for personal protection of the tester, designed to provide visual observation of the extinguisher under test.
(16) The employer shall maintain and provide upon request to the Assistant Secretary evidence that the required hydrostatic testing of fire extinguishers has been performed at the time intervals shown in Table L-1. Such evidence shall be in the form of a certification record which includes the date of the test, the signature of the person who performed the test and the serial number, or other identifier, of the fire extinguisher that was tested. Such records shall be kept until the extinguisher is hydrostatically retested at the time interval specified in Table L-1 or until the extinguisher is taken out of service, whichever comes first.
(g) Training and education. (1) Where the employer has provided portable fire extinguishers for employee use in the workplace, the employer shall also provide an educational program to familiarize employees with the general principles of fire extinguisher use and the hazards involved with incipient stage fire fighting.
(2) The employer shall provide the education required in paragraph (g)(1) of this section upon initial employment and at least annually thereafter.
(3) The employer shall provide employees who have been designated to use fire fighting equipment as part of an emergency action plan with training in the use of the appropriate equipment.
(4) The employer shall provide the training required in paragraph (g)(3) of this section upon initial assignment to the designated group of employees and at least annually thereafter.
[45 FR 60708, Sept. 12, 1980; 46 FR 24557, May 1, 1981, as amended at 51 FR 34560, Sept. 29, 1986; 61 FR 9239, Mar. 7, 1996; 67 FR 67964, Nov. 7, 2002]
- yuen.law: ecfr 29 CFR 1910
- yuen.asof: 2026-01-01
- yuen.sha256: c2a9ce966c7e2269
