# 支払日, 支払の方針

# Specification: 支払日
- yurai.file: 支払.req
- yurai.version: 1
- yurai.description: テストの材料。版が二つある要件、置き換え、別のファイルの要件を元にした要件を書いたもの。例として決めた決まりで、実際の支払条件ではない

## month_end_close v1: 月末締め (yurai requirement)
請求書は月末で締める
- yurai.inForce: 2026-01-01..2027-03-31
- yurai.owner: 経理
- yurai.decided: decided 2025-12-01 by 経理 "締めを月末にそろえる。この材料のために決めたもの"
- yurai.waived: not verified "締め日は、月末の日付を返すだけなので、確かめる主張を置かない"
  approved 2026-10-03 by 経理 sha256:f96940c54fbf4ebe
- yurai.sha256: f96940c54fbf4ebe
- yurai.status: ok
- yurai satisfied by -> file "src/close.py"

## payment_day v1: 支払日 v1 (yurai requirement)
月末締め翌月末払い
- yurai.inForce: 2026-01-01..2027-03-31
- yurai.owner: 経理
- yurai.sha256: a7f6fcd60af6ec1b
- yurai.status: ok
- yurai from -> payment_policy v1
- yurai satisfied by -> file "src/pay.py"
- yurai verified by -> file "tests/test_pay.py"

## payment_day v2: 支払日 v2 (yurai requirement)
20 日締め翌月 10 日払い
- yurai.inForce: 2027-04-01..
- yurai.owner: 経理
- yurai.decided: decided 2026-10-03 by 経理 "2027 年 4 月から、締めを 20 日に変える。この材料のために決めたもの"
- yurai.sha256: 40f44f65d5515257
- yurai.status: ok
- yurai from -> payment_policy v1
- yurai satisfied by -> file "src/pay.py"
- yurai verified by -> file "tests/test_pay.py"
- yurai replaces -> month_end_close v1

# Specification: 支払の方針
- yurai.file: 方針.req
- yurai.version: 1
- yurai.description: テストの材料。支払日の要件の元になる方針を、例の約款から読んで決めたもの。例として書いたもので、実際の支払条件ではない

## payment_policy v1: 支払の方針 (yurai requirement)
受け取った請求書の代金は、締め日から 60 日以内に支払う
- yurai.owner: 経理
- yurai.decided: decided 2026-09-01 by 経理 "約款の第 4 条の「締め日から」を、締め日の翌日から数えると読む。この材料のために決めたもの"
- yurai.sha256: 4170875c93bcbd5f
- yurai.status: ok
- yurai from -> 約款
- yurai satisfied by -> file "src/pay.py"
- yurai verified by -> file "tests/test_pay.py"

# Specification: sources

## 約款 (yurai source)
- yurai.file: docs/約款.md
- yurai.url: https://example.org/terms.md
- yurai.sha256: ebf6db0789a91bcf

# Specification: artifacts

## file "src/close.py" (yurai artifact)
- yurai.sha256: 9eef6de9a1d41e52
- yurai.end: file

## file "src/pay.py" (yurai artifact)
- yurai.sha256: e71c187c98c06bc8
- yurai.end: file

## file "tests/test_pay.py" (yurai artifact)
- yurai.sha256: d339e68dbbe8a90a
- yurai.end: file
