# 民法の期間

# Specification: 民法の期間
- yurai.file: 民法の期間.req
- yurai.version: 1
- yurai.description: koyomi の例「民法の期間.cal」の日付が、民法のどの条から来たかを書いたテストの材料。出典は自分で写して固定し、成果物はファイルとして読む。例として書いたもので、法令の読み方を示すものではない

## first_day v1: 起算日 (yurai requirement)
日、週、月又は年によって期間を定めたときは、期間の初日は、算入しない。ただし、その期間が午前零時から始まるときは、この限りでない
- yurai.inForce: 2026-10-01..
- yurai.owner: 法務
- yurai.waived: not verified "初日を算入しないことは、koyomi doc のページで、条文と言い直しを見比べて確かめる。この材料に、それを確かめる条件は無い"
  approved 2026-10-03 by 法務 sha256:a9ebc73907faddc8
- yurai.sha256: a9ebc73907faddc8
- yurai.status: ok
- yurai from -> 民法 第140条
- yurai satisfied by -> file "民法の期間.cal"

## last_day v1: 満了日 (yurai requirement)
月によって期間を定めたときは、最後の月においてその起算日に応当する日の前日の終わりに満了する。応当する日がないときは、その月の末日の終わりに満了する
- yurai.inForce: 2026-10-01..
- yurai.owner: 法務
- yurai.waived: not verified "条文の場合分けをそのまま書いた関数と、起点 2000〜2027 年のすべての日と月数 1〜12 で一致することを、koyomi の設計の段階の試作が確かめた。この材料の中に、それを確かめる条件は無い"
  approved 2026-10-03 by 法務 sha256:465b83ed8c251406
- yurai.sha256: 465b83ed8c251406
- yurai.status: ok
- yurai from -> 民法 第141条
- yurai from -> 民法 第143条
- yurai satisfied by -> file "民法の期間.cal"

## last_day_142 v1: 満了日_142条 (yurai requirement)
期間の末日が日曜日、国民の祝日に関する法律に規定する休日その他の休日に当たるときは、その日に取引をしない慣習がある場合に限り、期間は、その翌日に満了する
- yurai.inForce: 2026-10-01..
- yurai.owner: 法務
- yurai.decided: decided 2026-10-03 by 法務 "「その翌日」は文字どおり末日の翌日と読み、翌日も休みでもそれ以上は動かさない。この材料のために決めたもので、法令の読み方を示すものではない"
- yurai.waived: not verified "koyomi の条件「142条の満了日は満了日以後」が確かめているが、この材料は .cal をファイルとして読むので、その条件を名指さない"
  approved 2026-10-03 by 法務 sha256:d4f2d2a67322df17
- yurai.sha256: d4f2d2a67322df17
- yurai.status: ok
- yurai from -> 民法 第142条
- yurai satisfied by -> file "民法の期間.cal"

# Specification: sources

## 民法 第140条 (yurai source)
第百四十条 日、週、月又は年によって期間を定めたときは、期間の初日は、算入しない。ただし、その期間が午前零時から始まるときは、この限りでない。
- yurai.law: egov 129AC0000000089
- yurai.asof: 2026-10-01
- yurai.revision: 129AC0000000089_20260624_508AC0000000045
- yurai.sha256: e880059021fbb67d

## 民法 第141条 (yurai source)
（期間の満了）
第百四十一条 前条の場合には、期間は、その末日の終了をもって満了する。
- yurai.law: egov 129AC0000000089
- yurai.asof: 2026-10-01
- yurai.revision: 129AC0000000089_20260624_508AC0000000045
- yurai.sha256: 0575c131b9f08063

## 民法 第142条 (yurai source)
第百四十二条 期間の末日が日曜日、国民の祝日に関する法律（昭和二十三年法律第百七十八号）に規定する休日その他の休日に当たるときは、その日に取引をしない慣習がある場合に限り、期間は、その翌日に満了する。
- yurai.law: egov 129AC0000000089
- yurai.asof: 2026-10-01
- yurai.revision: 129AC0000000089_20260624_508AC0000000045
- yurai.sha256: fc8c35a0769d3b35

## 民法 第143条 (yurai source)
（暦による期間の計算）
第百四十三条 週、月又は年によって期間を定めたときは、その期間は、暦に従って計算する。
２ 週、月又は年の初めから期間を起算しないときは、その期間は、最後の週、月又は年においてその起算日に応当する日の前日に満了する。ただし、月又は年によって期間を定めた場合において、最後の月に応当する日がないときは、その月の末日に満了する。
- yurai.law: egov 129AC0000000089
- yurai.asof: 2026-10-01
- yurai.revision: 129AC0000000089_20260624_508AC0000000045
- yurai.sha256: 6950bdfb988439b6

# Specification: artifacts

## file "民法の期間.cal" (yurai artifact)
- yurai.sha256: c9b94eecde23e6b5
- yurai.end: file
